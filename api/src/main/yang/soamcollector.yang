module soamcollector {
    yang-version 1;
    namespace "urn:opendaylight:soamcollector";
    prefix "soam";

    import yang-ext { prefix ext; }
    
    import ietf-inet-types {
        prefix "inet";
    }

    import network-topology {
        prefix "nt";
    }

    revision "2016-11-23" {
        description "Initial revision of soamcollector model";
    }
    
    rpc get-history-stats {
        input {
            leaf ip-address {
                type inet:ip-address;
            }
            leaf community {
                type string;
            }
        }
        output {
            leaf results {
                type string;
            }
        }
    }

    grouping soamcollector-attrs {
        leaf snmp-community {
            type string;
        }
        leaf poll-interval {
            description "Polling interval in seconds";
            type uint32;
            default 60;
        }
    }

    augment "/nt:network-topology/nt:topology/nt:node" {
        ext:augment-identifier "soam-node";
        uses soamcollector-attrs;
    }

}
