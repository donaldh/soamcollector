/*
 * This module has been generated by smidump 0.4.8:
 *
 *      smidump -f yang P-BRIDGE-MIB
 *
 * Do not edit. Edit the source file instead!
 */

module P-BRIDGE-MIB {

  /*** NAMESPACE / PREFIX DEFINITION ***/

  namespace "urn:ietf:params:xml:ns:yang:smiv2:P-BRIDGE-MIB";
  prefix "p-bridge";

  /*** LINKAGE (IMPORTS / INCLUDES) ***/

  import BRIDGE-MIB { prefix "bridge-mib"; }
  import SNMPv2-TC  { prefix "smiv2"; }
  import ietf-yang-types { prefix "yang"; }

  /*** META INFORMATION ***/

  organization      
   "IETF Bridge MIB Working Group";

  contact           
   "Email:  bridge-mib@ietf.org
    ietfmibs@ops.ietf.org
    
    David Levi
    Postal: Nortel Networks
    4655 Great America Parkway
    Santa Clara, CA 95054
    USA
    Phone: +1 865 686 0432
    Email: dlevi@nortel.com
    
    David Harrington
    Postal: Effective Software
    50 Harding Rd.
    Portsmouth, NH 03801
    USA
    Phone: +1 603 436 8634
    Email: ietfdbh@comcast.net
    
    Les Bell
    Postal: Hemel Hempstead, Herts. HP2 7YU
    UK
    Email: elbell@ntlworld.com
    
    Vivian Ngai
    
    
    
    Email: vivian_ngai@acm.org
    
    Andrew Smith
    Postal: Beijing Harbour Networks
    Jiuling Building
    21 North Xisanhuan Ave.
    Beijing, 100089
    PRC
    Fax: +1 415 345 1827
    Email: ah_smith@acm.org
    
    Paul Langille
    Postal: Newbridge Networks
    5 Corporate Drive
    Andover, MA 01810
    USA
    Phone: +1 978 691 4665
    Email: langille@newbridge.com
    
    Anil Rijhsinghani
    Postal: Accton Technology Corporation
    5 Mount Royal Ave
    Marlboro, MA 01752
    USA
    Phone:
    Email: anil@accton.com
    
    Keith McCloghrie
    Postal: Cisco Systems, Inc.
    170 West Tasman Drive
    San Jose, CA 95134-1706
    USA
    Phone: +1 408 526 5260
    Email: kzm@cisco.com";

  description       
   "The Bridge MIB Extension module for managing Priority
    and Multicast Filtering, defined by IEEE 802.1D-1998,
    including Restricted Group Registration defined by
    IEEE 802.1t-2001.
    
    Copyright (C) The Internet Society (2006).  This version of
    this MIB module is part of RFC 4363; See the RFC itself for
    full legal notices.";

  revision "2006-01-09" {
    description     
     "Added dot1dPortRestrictedGroupRegistration.
      Deprecated pBridgePortGmrpGroup and pBridgeCompliance
      and added pBridgePortGmrpGroup2 and pBridgeCompliance2.";
  }
  revision "1999-08-25" {
    description     
     "The Bridge MIB Extension module for managing Priority
      and Multicast Filtering, defined by IEEE 802.1D-1998.
      
      Initial version, published as RFC 2674.";
  }

  /*** TYPE DEFINITIONS ***/

  typedef EnabledStatus {
    type enumeration {
      enum enabled  { value 1; }
      enum disabled { value 2; }
    }
    description     
     "A simple status value for the object.";
  }

  container dot1dExtBase {

    leaf dot1dDeviceCapabilities {
      type bits {
        bit dot1dExtendedFilteringServices { position 0; }
        bit dot1dTrafficClasses            { position 1; }
        bit dot1qStaticEntryIndividualPort { position 2; }
        bit dot1qIVLCapable                { position 3; }
        bit dot1qSVLCapable                { position 4; }
        bit dot1qHybridCapable             { position 5; }
        bit dot1qConfigurablePvidTagging   { position 6; }
        bit dot1dLocalVlanCapable          { position 7; }
      }
      description   
       "Indicates the optional parts of IEEE 802.1D and 802.1Q
        that are implemented by this device and are manageable
        through this MIB.  Capabilities that are allowed on a
        per-port basis are indicated in dot1dPortCapabilities.
        
        dot1dExtendedFilteringServices(0),
                              -- can perform filtering of
                              -- individual multicast addresses
                              -- controlled by GMRP.
        dot1dTrafficClasses(1),
                              -- can map user priority to
                              -- multiple traffic classes.
        dot1qStaticEntryIndividualPort(2),
                              -- dot1qStaticUnicastReceivePort &
                              -- dot1qStaticMulticastReceivePort
                              -- can represent non-zero entries.
        dot1qIVLCapable(3),   -- Independent VLAN Learning (IVL).
        dot1qSVLCapable(4),   -- Shared VLAN Learning (SVL).
        dot1qHybridCapable(5),
                              -- both IVL & SVL simultaneously.
        dot1qConfigurablePvidTagging(6),
                              -- whether the implementation
                              -- supports the ability to
                              -- override the default PVID
                              -- setting and its egress status
                              -- (VLAN-Tagged or Untagged) on
                              -- each port.
        dot1dLocalVlanCapable(7)
                              -- can support multiple local
                              -- bridges, outside of the scope
                              -- of 802.1Q defined VLANs.";
      reference     
       "ISO/IEC 15802-3 Section 5.2,
        IEEE 802.1Q/D11 Section 5.2, 12.10.1.1.3/b/2";
    }

    leaf dot1dTrafficClassesEnabled {
      type smiv2:TruthValue;
      config true;
      description   
       "The value true(1) indicates that Traffic Classes are
        enabled on this bridge.  When false(2), the bridge
        operates with a single priority level for all traffic.
        
        The value of this object MUST be retained across
        reinitializations of the management system.";
    }

    leaf dot1dGmrpStatus {
      type p-bridge:EnabledStatus;
      config true;
      description   
       "The administrative status requested by management for
        GMRP.  The value enabled(1) indicates that GMRP should
        be enabled on this device, in all VLANs, on all ports
        for which it has not been specifically disabled.  When
        disabled(2), GMRP is disabled, in all VLANs and on all
        ports, and all GMRP packets will be forwarded
        transparently.  This object affects both Applicant and
        Registrar state machines.  A transition from disabled(2)
        to enabled(1) will cause a reset of all GMRP state
        machines on all ports.
        
        The value of this object MUST be retained across
        reinitializations of the management system.";
    }

  }

  container dot1dPriority {


    /* XXX table comments here XXX */

    list dot1dUserPriorityRegenEntry {

      key "dot1dBasePort dot1dUserPriority";
      description   
       "A mapping of incoming User Priority to a Regenerated
        User Priority.";

      leaf dot1dBasePort {
        type leafref {
          path "/bridge-mib:dot1dBase/bridge-mib:dot1dBasePortEntry/bridge-mib:dot1dBasePort";
        }
        description 
         "Automagically generated leafref leaf.";
      }

      leaf dot1dUserPriority {
        type int32 {
          range "0..7";
        }
        description 
         "The User Priority for a frame received on this port.";
      }

      leaf dot1dRegenUserPriority {
        type int32 {
          range "0..7";
        }
        config true;
        description 
         "The Regenerated User Priority that the incoming User
          
          
          
          Priority is mapped to for this port.
          
          The value of this object MUST be retained across
          reinitializations of the management system.";
      }
    }


    /* XXX table comments here XXX */

    list dot1dTrafficClassEntry {

      key "dot1dBasePort dot1dTrafficClassPriority";
      description   
       "User Priority to Traffic Class mapping.";

      leaf dot1dBasePort {
        type leafref {
          path "/bridge-mib:dot1dBase/bridge-mib:dot1dBasePortEntry/bridge-mib:dot1dBasePort";
        }
        description 
         "Automagically generated leafref leaf.";
      }

      leaf dot1dTrafficClassPriority {
        type int32 {
          range "0..7";
        }
        description 
         "The Priority value determined for the received frame.
          This value is equivalent to the priority indicated in
          the tagged frame received, or one of the evaluated
          priorities, determined according to the media-type.
          
          
          
          For untagged frames received from Ethernet media, this
          value is equal to the dot1dPortDefaultUserPriority value
          for the ingress port.
          
          For untagged frames received from non-Ethernet media,
          this value is equal to the dot1dRegenUserPriority value
          for the ingress port and media-specific user priority.";
      }

      leaf dot1dTrafficClass {
        type int32 {
          range "0..7";
        }
        config true;
        description 
         "The Traffic Class the received frame is mapped to.
          
          The value of this object MUST be retained across
          reinitializations of the management system.";
      }
    }


    /* XXX table comments here XXX */

    list dot1dPortOutboundAccessPriorityEntry {

      key "dot1dBasePort dot1dRegenUserPriority";
      description   
       "Regenerated User Priority to Outbound Access Priority
        mapping.";

      leaf dot1dBasePort {
        type leafref {
          path "/bridge-mib:dot1dBase/bridge-mib:dot1dBasePortEntry/bridge-mib:dot1dBasePort";
        }
        description 
         "Automagically generated leafref leaf.";
      }
      leaf dot1dRegenUserPriority {
        type leafref {
          path "/p-bridge:dot1dPriority/p-bridge:dot1dUserPriorityRegenEntry/p-bridge:dot1dRegenUserPriority";
        }
        description 
         "Automagically generated leafref leaf.";
      }

      leaf dot1dPortOutboundAccessPriority {
        type int32 {
          range "0..7";
        }
        description 
         "The Outbound Access Priority the received frame is
          mapped to.";
      }
    }
  }

  container dot1dGarp {

  }

  container dot1dGmrp {

  }


  /* XXX table comments here XXX */

  augment "/bridge-mib:dot1dBase/bridge-mib:dot1dBasePortEntry" {
    description     
     "A set of capabilities information about this port
      indexed by dot1dBasePort.";

    leaf dot1dPortCapabilities {
      type bits {
        bit dot1qDot1qTagging                     { position 0; }
        bit dot1qConfigurableAcceptableFrameTypes { position 1; }
        bit dot1qIngressFiltering                 { position 2; }
      }
      description   
       "Indicates the parts of IEEE 802.1D and 802.1Q that are
        optional on a per-port basis, that are implemented by
        this device, and that are manageable through this MIB.
        
        dot1qDot1qTagging(0), -- supports 802.1Q VLAN tagging of
                              -- frames and GVRP.
        dot1qConfigurableAcceptableFrameTypes(1),
                              -- allows modified values of
                              -- dot1qPortAcceptableFrameTypes.
        dot1qIngressFiltering(2)
                              -- supports the discarding of any
                              -- frame received on a Port whose
                              -- VLAN classification does not
                              -- include that Port in its Member
                              -- set.";
      reference     
       "ISO/IEC 15802-3 Section 5.2,
        IEEE 802.1Q/D11 Section 5.2";
    }
  }


  /* XXX table comments here XXX */

  augment "/bridge-mib:dot1dBase/bridge-mib:dot1dBasePortEntry" {
    description     
     "A list of Default User Priorities for each port of a
      transparent bridge.  This is indexed by dot1dBasePort.";

    leaf dot1dPortDefaultUserPriority {
      type int32 {
        range "0..7";
      }
      config true;
      description   
       "The default ingress User Priority for this port.  This
        only has effect on media, such as Ethernet, that do not
        support native User Priority.
        
        The value of this object MUST be retained across
        reinitializations of the management system.";
    }

    leaf dot1dPortNumTrafficClasses {
      type int32 {
        range "1..8";
      }
      config true;
      description   
       "The number of egress traffic classes supported on this
        port.  This object may optionally be read-only.
        
        The value of this object MUST be retained across
        reinitializations of the management system.";
    }
  }


  /* XXX table comments here XXX */

  augment "/bridge-mib:dot1dBase/bridge-mib:dot1dBasePortEntry" {
    description     
     "GARP control information for a bridge port.";

    leaf dot1dPortGarpJoinTime {
      type smiv2:TimeInterval;
      config true;
      description   
       "The GARP Join time, in centiseconds.
        
        The value of this object MUST be retained across
        reinitializations of the management system.";
    }

    leaf dot1dPortGarpLeaveTime {
      type smiv2:TimeInterval;
      config true;
      description   
       "The GARP Leave time, in centiseconds.
        
        The value of this object MUST be retained across
        reinitializations of the management system.";
    }

    leaf dot1dPortGarpLeaveAllTime {
      type smiv2:TimeInterval;
      config true;
      description   
       "The GARP LeaveAll time, in centiseconds.
        
        The value of this object MUST be retained across
        reinitializations of the management system.";
    }
  }


  /* XXX table comments here XXX */

  augment "/bridge-mib:dot1dBase/bridge-mib:dot1dBasePortEntry" {
    description     
     "GMRP control and status information for a bridge port.";

    leaf dot1dPortGmrpStatus {
      type p-bridge:EnabledStatus;
      config true;
      description   
       "The administrative state of GMRP operation on this port.  The
        value enabled(1) indicates that GMRP is enabled on this port
        in all VLANs as long as dot1dGmrpStatus is also enabled(1).
        A value of disabled(2) indicates that GMRP is disabled on
        this port in all VLANs: any GMRP packets received will
        be silently discarded, and no GMRP registrations will be
        propagated from other ports.  Setting this to a value of
        enabled(1) will be stored by the agent but will only take
        effect on the GMRP protocol operation if dot1dGmrpStatus
        also indicates the value enabled(1).  This object affects
        all GMRP Applicant and Registrar state machines on this
        port.  A transition from disabled(2) to enabled(1) will
        cause a reset of all GMRP state machines on this port.
        
        The value of this object MUST be retained across
        reinitializations of the management system.";
    }

    leaf dot1dPortGmrpFailedRegistrations {
      type yang:counter32;
      description   
       "The total number of failed GMRP registrations, for any
        reason, in all VLANs, on this port.";
    }

    leaf dot1dPortGmrpLastPduOrigin {
      type yang:mac-address;
      description   
       "The Source MAC Address of the last GMRP message
        received on this port.";
    }

    leaf dot1dPortRestrictedGroupRegistration {
      type smiv2:TruthValue;
      config true;
      description   
       "The state of Restricted Group Registration on this port.
        If the value of this control is true(1), then creation
        of a new dynamic entry is permitted only if there is a
        Static Filtering Entry for the VLAN concerned, in which
        the Registrar Administrative Control value is Normal
        Registration.
        
        The value of this object MUST be retained across
        reinitializations of the management system.";
      reference     
       "IEEE 802.1t clause 10.3.2.3, 14.10.1.3.";
    }
  }

} /* end of module P-BRIDGE-MIB */
