/*
 * This module has been generated by smidump 0.4.8:
 *
 *      smidump -f yang IEEE8021-CFM-MIB
 *
 * Do not edit. Edit the source file instead!
 */

module IEEE8021-CFM-MIB {

  /*** NAMESPACE / PREFIX DEFINITION ***/

  namespace "urn:ietf:params:xml:ns:yang:smiv2:IEEE8021-CFM-MIB";
  prefix "ieee8021-cfm";

  /*** LINKAGE (IMPORTS / INCLUDES) ***/

  import IEEE8021-TC-MIB { prefix "ieee8021-tc"; }
  import IF-MIB          { prefix "if-mib"; }
  import LLDP-MIB        { prefix "lldp-mib"; }
  import Q-BRIDGE-MIB    { prefix "q-bridge"; }
  import SNMPv2-TC       { prefix "smiv2"; }
  import ietf-yang-types      { prefix "yang"; }

  /*** META INFORMATION ***/

  organization      
   "IEEE 802.1 Working Group";

  contact           
   "WG-URL:   http://grouper.ieee.org/groups/802/1/index.html
    WG-EMail: stds-802-1@ieee.org 
    
    Contact:  David Elie-Dit-Cosaque
       Postal: C/O IEEE 802.1 Working Group
               IEEE Standards Association
               445 Hoes Lane
               P.O. Box 1331
               Piscataway
               NJ 08855-1331
               USA
       E-mail: STDS-802-1-L@LISTSERV.IEEE.ORG
    
    Contact:  Norman Finn
       Postal: C/O IEEE 802.1 Working Group
               IEEE Standards Association
               445 Hoes Lane
               P.O. Box 1331
               Piscataway
               NJ 08855-1331
               USA
       E-mail: STDS-802-1-L@LISTSERV.IEEE.ORG";

  description       
   "Connectivity Fault Management module.
    
    Unless otherwise indicated, the references in this MIB
    module are to IEEE 802.1Q-2011.
    
    Copyright (C) IEEE.
    This version of this MIB module is part of IEEE802.1Q;
    see the draft itself for full legal notices.";

  revision "2011-02-27" {
    description     
     "Addition of support for ICC format and minor edits
      as part of 2011 revision of IEEE Std 802.1Q.";
  }
  revision "2008-11-18" {
    description     
     "Added new columns to the dot1agCfmMepTable to support new
      MEP functionality required for PBB-TE support.  Modified
      dot1agCfmMepDbTable to support new functionality requried
      for PBB-TE.  Modified conformance clauses to indicate objects
      needed for PBB-TE support.";
  }
  revision "2008-10-15" {
    description     
     "The IEEE8021-CFM-MIB Module was originally included in IEEE 
      802.1ag-2007. Some objects in this module are deprecated and 
      replaced by objects in the IEEE8021-CFM-V2-MIB module
      defined in 802.1ap.
      
      This revision is included in IEEE 802.1ap";
  }
  revision "2007-06-10" {
    description     
     "Included in IEEE 802.1ag-2007
      
      Copyright (C) IEEE802.1.";
  }

  /*** TYPE DEFINITIONS ***/

  typedef Dot1agCfmMaintDomainNameType {
    type enumeration {
      enum none              { value 1; }
      enum dnsLikeName       { value 2; }
      enum macAddressAndUint { value 3; }
      enum charString        { value 4; }
    }
    description     
     "A value that represents a type (and thereby the format)
      of a Dot1agCfmMaintDomainName.  The value can be one of
      the following:
      
      
      ieeeReserved(0)   Reserved for definition by IEEE 802.1
                        recommend to not use zero unless
                        absolutely needed.
      none(1)           No format specified, usually because
                        there is not (yet) a Maintenance
                        Domain Name. In this case, a zero
                        length OCTET STRING for the Domain
                        Name field is acceptable.
      dnsLikeName(2)    Domain Name like string, globally unique
                        text string derived from a DNS name.
      macAddrAndUint(3) MAC address + 2-octet (unsigned) integer.
      charString(4)     RFC2579 DisplayString, except that the
                        character codes 0-31 (decimal) are not
                        used.
      ieeeReserved(xx)  Reserved for definition by IEEE 802.1
                        xx values can be [5..31] and [64..255]
      ituReserved(xx)   Reserved for definition by  ITU-T Y.1731
                        xx values range from [32..63]
      
      To support future extensions, the Dot1agCfmMaintDomainNameType
      textual convention SHOULD NOT be sub-typed in object type
      definitions.  It MAY be sub-typed in compliance statements in
      order to require only a subset of these address types for a
      compliant implementation.
      
      Implementations MUST ensure that Dot1agCfmMaintDomainNameType
      objects and any dependent objects (e.g.,
      Dot1agCfmMaintDomainName objects) are consistent.  An
      inconsistentValue error MUST be generated if an attempt to
      change an Dot1agCfmMaintDomainNameType object would, for
      example, lead to an undefined Dot1agCfmMaintDomainName value.
      In particular,
      Dot1agCfmMaintDomainNameType/Dot1agCfmMaintDomainName pairs
      MUST be changed together if the nameType changes.";
    reference       
     "21.6.5, Table 21-19";
  }

  typedef Dot1agCfmMaintDomainName {
    type binary {
      length "1..43";
    }
    description     
     "Denotes a generic Maintenance Domain Name.
      
      A Dot1agCfmMaintDomainName value is always interpreted within
      the context of a Dot1agCfmMaintDomainNameType value.  Every
      usage of the Dot1agCfmMaintDomainName textual convention is
      required to specify the Dot1agCfmMaintDomainNameType object
      that provides the context.  It is suggested that the
      Dot1agCfmMaintDomainNameType object be logically registered
      before the object(s) that use the Dot1agCfmMaintDomainName
      textual convention, if they appear in the same logical row.
      
      The value of a Dot1agCfmMaintDomainName object MUST always
      be consistent with the value of the associated
      Dot1agCfmMaintDomainNameType object. Attempts to set
      an Dot1agCfmMaintDomainName object to a value inconsistent
      with the associated Dot1agCfmMaintDomainNameType MUST fail
      with an inconsistentValue error.
      
      When this textual convention is used as the syntax of an
      index object, there may be issues with the limit of 128
      sub-identifiers specified in SMIv2, IETF STD 58.  In this
      case, the object definition MUST include a 'SIZE' clause
      to limit the number of potential instance sub-identifiers;
      otherwise the applicable constraints MUST be stated in
      the appropriate conceptual row DESCRIPTION clauses, or
      in the surrounding documentation if there is no single
      DESCRIPTION clause that is appropriate.
      
      A value of none(1) in the associated
      Dot1agCfmMaintDomainNameType object means that no Maintenance
      Domain name is present, and the contents of the
      Dot1agCfmMaintDomainName object are meaningless.
      
      See the DESCRIPTION of the Dot1agCfmMaintAssocNameType
      TEXTUAL-CONVENTION for a discussion of the length limits on
      the Maintenance Domain name and Maintenance Association name.";
    reference       
     "21.6.5";
  }

  typedef Dot1agCfmMaintAssocNameType {
    type enumeration {
      enum primaryVid    { value 1; }
      enum charString    { value 2; }
      enum unsignedInt16 { value 3; }
      enum rfc2865VpnId  { value 4; }
      enum iccformat     { value 32; }
    }
    description     
     "A value that represents a type (and thereby the format)
      of a Dot1agCfmMaintAssocName.  The value can be one of
      the following:
      
      ieeeReserved(0)   Reserved for definition by IEEE 802.1
                        recommend to not use zero unless
                        absolutely needed.
      primaryVid(1)     Primary VLAN ID.
                        12 bits represented in a 2-octet integer:
                        - 4 least significant bits of the first
                          byte contains the 4 most significant 
                          bits of the 12 bits primary VID
                        - second byte contains the 8 least
                          significant bits of the primary VID
      
                               0 1 2 3 4 5 6 7 8
                               +-+-+-+-+-+-+-+-+
                               |0 0 0 0| (MSB) |
                               +-+-+-+-+-+-+-+-+
                               |  VID   LSB    |
                               +-+-+-+-+-+-+-+-+
      
      charString(2)     RFC2579 DisplayString, except that the
                        character codes 0-31 (decimal) are not
                        used. (1..45) octets
      unsignedInt16 (3) 2-octet integer/big endian
      rfc2865VpnId(4)   RFC 2685 VPN ID
                        3 octet VPN authority Organizationally
                        Unique Identifier followed by 4 octet VPN
                        index identifying VPN according to the OUI:
      
                               0 1 2 3 4 5 6 7 8
                               +-+-+-+-+-+-+-+-+
                               | VPN OUI (MSB) |
                               +-+-+-+-+-+-+-+-+
                               |   VPN OUI     |
                               +-+-+-+-+-+-+-+-+
                               | VPN OUI (LSB) |
                               +-+-+-+-+-+-+-+-+
                               |VPN Index (MSB)|
                               +-+-+-+-+-+-+-+-+
                               |  VPN Index    |
                               +-+-+-+-+-+-+-+-+
                               |  VPN Index    |
                               +-+-+-+-+-+-+-+-+
                               |VPN Index (LSB)|
                               +-+-+-+-+-+-+-+-+
      
      ieeeReserved(xx)  Reserved for definition by IEEE 802.1
                        xx values can be [5..31] and [64..255]
      ICCformat(32)     ICC-based format as specified in ITU-T Y.1731
      ituReserved(xx)   Reserved for definition by  ITU-T Y.1731
                        xx values range from [33..63]
      
      To support future extensions, the Dot1agCfmMaintAssocNameType
      textual convention SHOULD NOT be sub-typed in object type
      definitions.  It MAY be sub-typed in compliance statements in
      order to require only a subset of these address types for a
      compliant implementation.
      
      Implementations MUST ensure that Dot1agCfmMaintAssocNameType
      objects and any dependent objects (e.g.,
      Dot1agCfmMaintAssocName objects) are consistent.  An
      inconsistentValue error MUST be generated if an attempt to
      change an Dot1agCfmMaintAssocNameType object would, for
      example, lead to an undefined Dot1agCfmMaintAssocName value.
      In particular,
      Dot1agCfmMaintAssocNameType/Dot1agCfmMaintAssocName pairs
      MUST be changed together if the nameType changes.
      
      The Maintenance Domain name and Maintenance Association name,
      when put together into the CCM PDU, MUST total 48 octets or
      less.  If the Dot1agCfmMaintDomainNameType object contains
      none(1), then the Dot1agCfmMaintAssocName object MUST be
      45 octets or less in length.  Otherwise, the length of
      the Dot1agCfmMaintDomainName object plus the length of the
      Dot1agCfmMaintAssocName object, added together, MUST total
      less than or equal to 44 octets.";
    reference       
     "21.6.5.4, Table 21-20";
  }

  typedef Dot1agCfmMaintAssocName {
    type binary {
      length "1..45";
    }
    description     
     "Denotes a generic Maintenance Association Name. It is the
      part of the Maintenance Association Identifier which is
      unique within the Maintenance Domain Name and is appended
      to the Maintenance Domain Name to form the Maintenance
      Association Identifier (MAID).
      
      A Dot1agCfmMaintAssocName value is always interpreted within
      the context of a Dot1agCfmMaintAssocNameType value.  Every
      usage of the Dot1agCfmMaintAssocName textual convention is
      required to specify the Dot1agCfmMaintAssocNameType object
      that provides the context.  It is suggested that the
      Dot1agCfmMaintAssocNameType object be logically registered
      before the object(s) that use the Dot1agCfmMaintAssocName
      textual convention, if they appear in the same logical row.
      
      The value of a Dot1agCfmMaintAssocName object MUST 
      always be consistent with the value of the associated
      Dot1agCfmMaintAssocNameType object. Attempts to set
      an Dot1agCfmMaintAssocName object to a value inconsistent
      with the associated Dot1agCfmMaintAssocNameType MUST fail
      with an inconsistentValue error.
      
      When this textual convention is used as the syntax of an
      index object, there may be issues with the limit of 128
      sub-identifiers specified in SMIv2, IETF STD 58.  In this
      case, the object definition MUST include a 'SIZE' clause
      to limit the number of potential instance sub-identifiers;
      otherwise the applicable constraints MUST be stated in
      the appropriate conceptual row DESCRIPTION clauses, or
      in the surrounding documentation if there is no single
      DESCRIPTION clause that is appropriate.";
    reference       
     "802.1ag clauses 21.6.5.4, 21.6.5.5, 21.6.5.6";
  }

  typedef Dot1agCfmMDLevel {
    type int32 {
      range "0..7";
    }
    description     
     "Integer identifying the Maintenance Domain Level (MD Level).
      Higher numbers correspond to higher Maintenance Domains,
      those with the greatest physical reach, with the highest
      values for customers' CFM PDUs.  Lower numbers correspond
      to lower Maintenance Domains, those with more limited
      physical reach, with the lowest values for CFM PDUs
      protecting single bridges or physical links.";
    reference       
     "802.1ag clauses 18.3, 21.4.1";
  }

  typedef Dot1agCfmMDLevelOrNone {
    type int32 {
      range "-1..7";
    }
    description     
     "Integer identifying the Maintenance Domain Level (MD Level).
      Higher numbers correspond to higher Maintenance Domains,
      those with the greatest physical reach, with the highest
      values for customers' CFM packets.  Lower numbers correspond
      to lower Maintenance Domains, those with more limited
      physical reach, with the lowest values for CFM PDUs
      protecting single bridges or physical links.
      
      The value (-1) is reserved to indicate that no MA Level has
      been assigned.";
    reference       
     "802.1ag clauses 18.3, 12.14.3.1.3:c";
  }

  typedef Dot1agCfmMpDirection {
    type enumeration {
      enum down { value 1; }
      enum up   { value 2; }
    }
    description     
     "Indicates the direction in which the Maintenance
      association (MEP or MIP) faces on the bridge port:
      
      down(1)    Sends Continuity Check Messages away from the
                 MAC Relay Entity.
      up(2)      Sends Continuity Check Messages towards the
                 MAC Relay Entity.";
    reference       
     "802.1ag clauses 12.14.6.3.2:c";
  }

  typedef Dot1agCfmPortStatus {
    type enumeration {
      enum psNoPortStateTLV { value 0; }
      enum psBlocked        { value 1; }
      enum psUp             { value 2; }
    }
    description     
     "An enumerated value from he Port Status TLV from the last CCM
      received from the last MEP. It indicates the ability of the
      Bridge Port on which the transmitting MEP resides to pass
      ordinary data, regardless of the status of the MAC
      (Table 21-10).
      
      psNoPortStateTLV(0) Indicates either that no CCM has been
                          received or that no port status TLV was
                          present in the last CCM received.
      
      psBlocked(1)        Ordinary data cannot pass freely through
                          the port on which the remote MEP resides.
                          Value of enableRmepDefect is equal to
                          false.
      
      psUp(2):            Ordinary data can pass freely through
                          the port on which the remote MEP resides.
                          Value of enableRmepDefect is equal to
                          true.
      
      NOTE: A 0 value is used for psNoPortStateTLV, so that
            additional code points can be added in a manner
            consistent with the Dot1agCfmInterfaceStatus textual
            convention.";
    reference       
     "12.14.7.6.3:f, 20.19.3 and 21.5.4";
  }

  typedef Dot1agCfmInterfaceStatus {
    type enumeration {
      enum isNoInterfaceStatusTLV { value 0; }
      enum isUp                   { value 1; }
      enum isDown                 { value 2; }
      enum isTesting              { value 3; }
      enum isUnknown              { value 4; }
      enum isDormant              { value 5; }
      enum isNotPresent           { value 6; }
      enum isLowerLayerDown       { value 7; }
    }
    description     
     "An enumerated value from the Interface Status TLV from the 
      last CCM received from the last MEP. It indicates the status
      of the Interface within which the MEP transmitting the CCM
      is configured, or the next lower Interface in the Interface
      Stack, if the MEP is not configured within an Interface.
      
      isNoInterfaceStatusTLV(0)  Indicates either that no CCM has been
                        received or that no interface status TLV
                        was present in the last CCM received.
      
      isUp(1)               The interface is ready to pass packets.
      
      isDown(2)             The interface cannot pass packets
      
      isTesting(3)          The interface is in some test mode.
      
      isUnknown(4)          The interface status cannot be determined
                        for some reason.
      
      isDormant(5)          The interface is not in a state to pass
                        packets but is in a pending state, waiting
                        for some external event.
      
      isNotPresent(6)       Some component of the interface is missing
      
      isLowerLayerDown(7)   The interface is down due to state of the
                        lower layer interfaces
      
      NOTE: A 0 value is used for isNoInterfaceStatusTLV, so that
            these code points can be kept consistent with new code
            points added to ifOperStatus in the IF-MIB.";
    reference       
     "12.14.7.6.3:g, 20.19.4 and 21.5.5";
  }

  typedef Dot1agCfmHighestDefectPri {
    type enumeration {
      enum none         { value 0; }
      enum defRDICCM    { value 1; }
      enum defMACstatus { value 2; }
      enum defRemoteCCM { value 3; }
      enum defErrorCCM  { value 4; }
      enum defXconCCM   { value 5; }
    }
    description     
     "An enumerated value, equal to the contents of the variable
      highestDefect (20.33.9 and Table 20-1), indicating the
      highest-priority defect that has been present since the MEP
      Fault Notification Generator State Machine was last in the 
      FNG_RESET state, either:
      
      none(0)           no defects since FNG_RESET
      defRDICCM(1)      DefRDICCM
      defMACstatus(2)   DefMACstatus
      defRemoteCCM(3)   DefRemoteCCM
      defErrorCCM(4)    DefErrorCCM
      defXconCCM(5)     DefXconCCM
      
      The value 0 is used for no defects so that additional higher
      priority values can be added, if needed, at a later time, and
      so that these values correspond with those in
      Dot1agCfmLowestAlarmPri.";
    reference       
     "20.1.2, 12.14.7.7.2:c and 20.33.9";
  }

  typedef Dot1agCfmLowestAlarmPri {
    type enumeration {
      enum allDef        { value 1; }
      enum macRemErrXcon { value 2; }
      enum remErrXcon    { value 3; }
      enum errXcon       { value 4; }
      enum xcon          { value 5; }
      enum noXcon        { value 6; }
    }
    description     
     "An integer value specifying the lowest priority defect
      that is allowed to generate a Fault Alarm (20.9.5), either:
      
      allDef(1)           DefRDICCM, DefMACstatus, DefRemoteCCM,
                          DefErrorCCM, and DefXconCCM;
      macRemErrXcon(2)    Only DefMACstatus, DefRemoteCCM,
                          DefErrorCCM, and DefXconCCM (default);
      remErrXcon(3)       Only DefRemoteCCM, DefErrorCCM,
                          and DefXconCCM;
      errXcon(4)          Only DefErrorCCM and DefXconCCM;
      xcon(5)             Only DefXconCCM; or
      noXcon(6)           No defects DefXcon or lower are to be
                          reported;";
    reference       
     "12.14.7.1.3:k and 20.9.5";
  }

  typedef Dot1agCfmMepId {
    type uint32 {
      range "1..8191";
    }
    description     
     "Maintenance association End Point Identifier (MEPID): A small
      integer, unique over a given Maintenance Association,
      identifying a specific MEP.";
    reference       
     "802.1ag clauses 3.19 and 19.2.1";
  }

  typedef Dot1agCfmMepIdOrZero {
    type uint32 {
      range "0..8191";
    }
    description     
     "Maintenance association End Point Identifier (MEPID): A small
      integer, unique over a given Maintenance Association,
      identifying a specific MEP.
      
      The special value 0 is allowed to indicate special cases, for
      example that no MEPID is configured.
      
      Whenever an object is defined with this SYNTAX, then the
      DESCRIPTION clause of such an object MUST specify what the
      special value of 0 means.";
    reference       
     "19.2.1";
  }

  typedef Dot1agCfmMhfCreation {
    type enumeration {
      enum defMHFnone     { value 1; }
      enum defMHFdefault  { value 2; }
      enum defMHFexplicit { value 3; }
      enum defMHFdefer    { value 4; }
    }
    description     
     "Indicates if the Management Entity can create MHFs.
      The valid values are:
      
      defMHFnone(1)      No MHFs can be created for this VID.
      defMHFdefault(2)   MHFs can be created on this VID on any
                         Bridge port through which this VID can
                         pass.
      defMHFexplicit(3)  MHFs can be created for this VID only on
                         Bridge ports through which this VID can
                         pass, and only if a MEP is created at some
                         lower MD Level.
      defMHFdefer(4)     The creation of MHFs is determined by the
                         corresponding Maintenance Domain variable
                         (dot1agCfmMaCompMhfCreation).";
    reference       
     "12.14.5.1.3:c and 22.2.3";
  }

  typedef Dot1agCfmIdPermission {
    type enumeration {
      enum sendIdNone          { value 1; }
      enum sendIdChassis       { value 2; }
      enum sendIdManage        { value 3; }
      enum sendIdChassisManage { value 4; }
      enum sendIdDefer         { value 5; }
    }
    description     
     "Indicates what, if anything, is to be included in the Sender
      ID TLV transmitted in CCMs, LBMs, LTMs, and LTRs.  The valid
      values are:
      
      sendIdNone(1)      The Sender ID TLV is not to be sent.
      sendIdChassis(2)   The Chassis ID Length, Chassis ID
                         Subtype, and Chassis ID fields of  the
                         Sender ID TLV are to be sent.
      sendIdManage(3)    The Management Address Length and
                         Management Address of the Sender ID TLV
                         are to be sent.
      sendIdChassisManage(4) The Chassis ID Length, Chassis ID
                         Subtype, Chassis ID, Management Address
                         Length and Management Address fields are
                         all to be sent.
      sendIdDefer(5)     The contents of the Sender ID TLV are
                         determined by the corresponding
                         Maintenance Domain variable
                         (dot1agCfmMaCompIdPermission).";
    reference       
     "12.14.6.1.3:d and 21.5.3";
  }

  typedef Dot1agCfmCcmInterval {
    type enumeration {
      enum intervalInvalid { value 0; }
      enum interval300Hz   { value 1; }
      enum interval10ms    { value 2; }
      enum interval100ms   { value 3; }
      enum interval1s      { value 4; }
      enum interval10s     { value 5; }
      enum interval1min    { value 6; }
      enum interval10min   { value 7; }
    }
    description     
     "Indicates the interval at which CCMs are sent by a MEP.
      The possible values are:
      intervalInvalid(0) No CCMs are sent (disabled).
      interval300Hz(1)   CCMs are sent every 3 1/3 milliseconds
                         (300Hz).
      interval10ms(2)    CCMs are sent every 10 milliseconds.
      interval100ms(3)   CCMs are sent every 100 milliseconds.
      interval1s(4)      CCMs are sent every 1 second.
      interval10s(5)     CCMs are sent every 10 seconds.
      interval1min(6)    CCMs are sent every minute.
      interval10min(7)   CCMs are sent every 10 minutes.
      
      Note: enumerations start at zero to match the 'CCM Interval
            field' protocol field.";
    reference       
     "802.1ag clauses 12.14.6.1.3:e, 20.8.1 and 21.6.1.3";
  }

  typedef Dot1agCfmFngState {
    type enumeration {
      enum fngReset          { value 1; }
      enum fngDefect         { value 2; }
      enum fngReportDefect   { value 3; }
      enum fngDefectReported { value 4; }
      enum fngDefectClearing { value 5; }
    }
    description     
     "Indicates the diferent states of the MEP Fault Notification
      Generator State Machine.
      
      fngReset(1)            No defect has been present since the
                             dot1agCfmMepFngResetTime timer
                             expired, or since the state machine
                             was last reset.
      
      fngDefect(2)           A defect is present, but not for a
                             long enough time to be reported 
                             (dot1agCfmMepFngAlarmTime).
      
      fngReportDefect(3)     A momentary state during which the
                             defect is reported by sending a
                             dot1agCfmFaultAlarm notification,
                             if that action is enabled.
      
      fngDefectReported(4)   A defect is present, and some defect
                             has been reported.
      
      fngDefectClearing(5)   No defect is present, but the
                             dot1agCfmMepFngResetTime timer has
                             not yet expired.";
    reference       
     "12.14.7.1.3:f and 20.35";
  }

  typedef Dot1agCfmRelayActionFieldValue {
    type enumeration {
      enum rlyHit  { value 1; }
      enum rlyFdb  { value 2; }
      enum rlyMpdb { value 3; }
    }
    description     
     "Possible values the Relay action field can take.";
    reference       
     "802.1ag clauses 12.14.7.5.3:g, 20.36.2.5, 21.9.5, and
      Table 21-27";
  }

  typedef Dot1agCfmIngressActionFieldValue {
    type enumeration {
      enum ingNoTlv   { value 0; }
      enum ingOk      { value 1; }
      enum ingDown    { value 2; }
      enum ingBlocked { value 3; }
      enum ingVid     { value 4; }
    }
    description     
     "Possible values returned in the ingress action field.";
    reference       
     "802.1ag clauses 12.14.7.5.3:g, 20.36.2.6, 21.9.8.1, and
      Table 21-30";
  }

  typedef Dot1agCfmEgressActionFieldValue {
    type enumeration {
      enum egrNoTlv   { value 0; }
      enum egrOK      { value 1; }
      enum egrDown    { value 2; }
      enum egrBlocked { value 3; }
      enum egrVid     { value 4; }
    }
    description     
     "Possible values returned in the egress action field";
    reference       
     "802.1ag clauses 12.14.7.5.3:o, 20.36.2.10, 21.9.9.1, and
      Table 21-32";
  }

  typedef Dot1agCfmRemoteMepState {
    type enumeration {
      enum rMepIdle   { value 1; }
      enum rMepStart  { value 2; }
      enum rMepFailed { value 3; }
      enum rMepOk     { value 4; }
    }
    description     
     "Operational state of the remote MEP state machine.  This
      state machine monitors the reception of valid CCMs from a
      remote MEP with a specific MEPID.  It uses a timer that
      expires in 3.5 times the length of time indicated by the
      dot1agCfmMaNetCcmInterval object.
      
      rMepIdle(1)            Momentary state during reset.
      
      rMepStart(2)           The timer has not expired since the
                             state machine was reset, and no valid
                             CCM has yet been received.
      
      rMepFailed(3)          The timer has expired, both since the
                             state machine was reset, and since a
                             valid CCM was received.
      
      rMepOk(4)              The timer has not expired since a
                             valid CCM was received.";
    reference       
     "802.1ag clauses 12.14.7.6.3:b, 20.22";
  }

  typedef Dot1afCfmIndexIntegerNextFree {
    type uint32 {
      range "0..4294967295";
    }
    description     
     "An integer which may be used as a new Index in a table.
      
      The special value of 0 indicates that no more new entries can
      be created in the relevant table.
      
      When a MIB is used for configuration, an object with this
      SYNTAX always contains a legal value (if non-zero) for an
      index that is not currently used in the relevant table. The
      Command Generator (Network Management Application) reads this
      variable and uses the (non-zero) value read when creating a
      new row with an SNMP SET.  When the SET is performed, the
      Command Responder (agent) MUST determine whether the value is
      indeed still unused; Two Network Management Applications may
      attempt to create a row (configuration entry) simultaneously
      and use the same value. If it is currently unused, the SET
      succeeds and the Command Responder (agent) changes the value
      of this object, according to an implementation-specific
      algorithm.  If the value is in use, however, the SET fails.
      The Network Management Application MUST then re-read this
      variable to obtain a new usable value.
      
      An OBJECT-TYPE definition using this SYNTAX MUST specify the
      relevant table for which the object is providing this
      functionality.";
  }

  typedef Dot1agCfmMepDefects {
    type bits {
      bit bDefRDICCM    { position 0; }
      bit bDefMACstatus { position 1; }
      bit bDefRemoteCCM { position 2; }
      bit bDefErrorCCM  { position 3; }
      bit bDefXconCCM   { position 4; }
    }
    description     
     "A MEP can detect and report a number of defects, and multiple
      defects can be present at the same time. These defects are:
      
      bDefRDICCM(0) A remote MEP is reported the RDI bit in its
                   last CCM.
      bDefMACstatus(1) Either some remote MEP is reporting its
                   Interface Status TLV as not isUp, or all remote
                   MEPs are reporting a Port Status TLV that
                   contains some value other than psUp.
      bDefRemoteCCM(2) The MEP is not receiving valid CCMs from at
                   least one of the remote MEPs.
      bDefErrorCCM(3) The MEP has received at least one invalid CCM
                   whose CCM Interval has not yet timed out.
      bDefXconCCM(4) The MEP has received at least one CCM from
                   either another MAID or a lower MD Level whose
                   CCM Interval has not yet timed out.";
    reference       
     "802.1ag clauses 12.14.7.1.3:o, 12.14.7.1.3:p, 12.14.7.1.3:q,
      12.14.7.1.3:r, and 12.14.7.1.3:s.";
  }

  typedef Dot1agCfmConfigErrors {
    type bits {
      bit cfmLeak          { position 0; }
      bit conflictingVids  { position 1; }
      bit excessiveLevels  { position 2; }
      bit overlappedLevels { position 3; }
    }
    description     
     "While making the MIP creation evaluation described in 802.1ag
      clause 22.2.3, the management entity can encounter errors in
      the configuration. These are possible errors that can be
      encountered:
      
      CFMleak(0)   MA x is associated with a specific VID list,
                   one or more of the VIDs in MA x can pass through
                   the Bridge Port, no Down MEP is configured on
                   any Bridge Port for MA x, and some other MA y,
                   at a higher MD Level than MA x, and associated
                   with at least one of the VID(s) also in MA x,
                   does have a MEP configured on the Bridge Port.
      
      conflictingVids(1)  MA x is associated with a specific VID
                   list, an Up MEP is configured on MA x on the
                   Bridge Port, and some other MA y, associated
                   with at least one of the VID(s) also in MA x,
                   also has an Up MEP configured on some Bridge
                   Port.
      
      ExcessiveLevels(2)  The number of different MD Levels at
                   which MIPs are to be created on this port
                   exceeds the Bridge's capabilities (see
                   subclause 22.3).
      
      OverlappedLevels(3) A MEP is created for one VID at one MD
                   Level, but a MEP is configured on another
                   VID at that MD Level or higher, exceeding
                   the Bridge's capabilities.";
    reference       
     "12.14.4.1.3:b and clauses 22.2.3 and 22.2.4";
  }

  typedef Dot1agCfmPbbComponentIdentifier {
    type uint32 {
      range "1..4294967295";
    }
    description     
     "A Provider Backbone Bridge (PBB) can comprise a number of
      components, each of which can be managed in a manner
      essentially equivalent to an 802.1Q bridge.  In order to access
      these components easily, an index is used in a number of
      tables.  If any two tables are indexed by
      Dot1agCfmPbbComponentIdentifier, then entries in those tables
      indexed by the same value of Dot1agCfmPbbComponentIdentifier
      correspond to the same component.";
    reference       
     "12.3 l)";
  }

  container dot1agCfmDefaultMd {

    leaf dot1agCfmDefaultMdDefLevel {
      type ieee8021-cfm:Dot1agCfmMDLevel;
      config true;
      description   
       "A value indicating the MD Level at which MHFs are to be
        created, and Sender ID TLV transmission by those MHFs is to
        be controlled, for each dot1agCfmDefaultMdEntry whose
        dot1agCfmDefaultMdLevel object contains the value -1.
        
        After this initialization, this object needs to be persistent
        upon reboot or restart of a device.
        **NOTE: this object is deprecated due to re-indexing of the 
        table.";
      reference     
       "12.14.3.1.3:c, 12.14.3.2.2:b";
    }

    leaf dot1agCfmDefaultMdDefMhfCreation {
      type ieee8021-cfm:Dot1agCfmMhfCreation;
      config true;
      description   
       "A value indicating if the Management entity can create MHFs
        (MIP Half Function) for the VID, for each
        dot1agCfmDefaultMdEntry whose dot1agCfmDefaultMdMhfCreation
        object contains the value defMHFdefer.  Since, in this
        variable, there is no encompassing Maintenance Domain, the
        value defMHFdefer is not allowed.
        
        After this initialization, this object needs to be persistent
        upon reboot or restart of a device.";
      reference     
       "12.14.3.1.3:d";
    }

    leaf dot1agCfmDefaultMdDefIdPermission {
      type ieee8021-cfm:Dot1agCfmIdPermission;
      config true;
      description   
       "Enumerated value indicating what, if anything, is to be
        included in the Sender ID TLV (21.5.3) transmitted by MHFs
        created by the Default Maintenance Domain, for each
        dot1agCfmDefaultMdEntry whose dot1agCfmDefaultMdIdPermission
        object contains the value sendIdDefer.  Since, in this
        variable, there is no encompassing Maintenance Domain, the
        value sendIdDefer is not allowed.
        
        After this initialization, this object needs to be persistent
        upon reboot or restart of a device.";
      reference     
       "12.14.3.1.3:e";
    }


    /* XXX table comments here XXX */

    list dot1agCfmDefaultMdEntry {

      key "dot1agCfmDefaultMdComponentId 
           dot1agCfmDefaultMdPrimaryVid";
      status deprecated;
      description   
       "The Default MD Level table entry.
        **NOTE: this object is deprecated due to re-indexing of the 
        table.";


      leaf dot1agCfmDefaultMdComponentId {
        type ieee8021-cfm:Dot1agCfmPbbComponentIdentifier;
        status deprecated;
        description 
         "The bridge component within the system to which the information
          in this dot1agCfmDefaultMdEntry applies.  If the system is not
          a Bridge, or if only one component is present in the Bridge,
          then this variable (index) MUST be equal to 1.
          **NOTE: this object is deprecated due to re-indexing of the 
          table.";
        reference   
         "12.3 l)";
      }

      leaf dot1agCfmDefaultMdPrimaryVid {
        type q-bridge:VlanId;
        status deprecated;
        description 
         "The Primary VID of the VLAN to which this entry's objects
          apply.
          **NOTE: this object is deprecated due to re-indexing of the 
          table.";
      }

      leaf dot1agCfmDefaultMdStatus {
        type smiv2:TruthValue;
        status deprecated;
        description 
         "State of this Default MD Level table entry.  True if there is
          no entry in the Maintenance Association table defining an MA
          for the same VLAN ID and MD Level as this table's entry, and
          on which MA an Up MEP is defined, else false.
          **NOTE: this object is deprecated due to re-indexing of the 
          table.";
        reference   
         "12.14.3.1.3:b";
      }

      leaf dot1agCfmDefaultMdLevel {
        type ieee8021-cfm:Dot1agCfmMDLevelOrNone;
        config true;
        status deprecated;
        description 
         "A value indicating the MD Level at which MHFs are to be
          created, and Sender ID TLV transmission by those MHFs is to
          be controlled, for the VLAN to which this entry's objects
          apply.  If this object has the value -1, the MD Level for MHF
          creation for this VLAN is controlled by
          dot1agCfmDefaultMdDefLevel.
          **NOTE: this object is deprecated due to re-indexing of the 
          table.";
        reference   
         "12.14.3.1.3:c, 12.14.3.2.2:b";
      }

      leaf dot1agCfmDefaultMdMhfCreation {
        type ieee8021-cfm:Dot1agCfmMhfCreation;
        config true;
        status deprecated;
        description 
         "A value indicating if the Management entity can create MHFs
          (MIP Half Function) for this VID at this MD Level.  If this
          object has the value defMHFdefer, MHF creation for this VLAN
          is controlled by dot1agCfmDefaultMdDefMhfCreation.
          
          The value of this variable is meaningless if the values of
          dot1agCfmDefaultMdStatus is false.
          **NOTE: this object is deprecated due to re-indexing of the 
          table.";
        reference   
         "12.14.3.1.3:d";
      }

      leaf dot1agCfmDefaultMdIdPermission {
        type ieee8021-cfm:Dot1agCfmIdPermission;
        config true;
        status deprecated;
        description 
         "Enumerated value indicating what, if anything, is to be
          included in the Sender ID TLV (21.5.3) transmitted by MHFs
          created by the Default Maintenance Domain.  If this object
          has the value sendIdDefer, Sender ID TLV transmission for
          this VLAN is controlled by dot1agCfmDefaultMdDefIdPermission.
          
          The value of this variable is meaningless if the values of
          dot1agCfmDefaultMdStatus is false.
          **NOTE: this object is deprecated due to re-indexing of the 
          table.";
        reference   
         "12.14.3.1.3:e";
      }
    }
  }

  container dot1agCfmMd {

    leaf dot1agCfmMdTableNextIndex {
      type ieee8021-cfm:Dot1afCfmIndexIntegerNextFree;
      description   
       "This object contains an unused value for dot1agCfmMdIndex in
        the dot1agCfmMdTable, or a zero to indicate that none exist.";
    }


    /* XXX table comments here XXX */

    list dot1agCfmMdEntry {

      key "dot1agCfmMdIndex";
      description   
       "The Maintenance Domain table entry. This entry is not lost
        upon reboot. It is backed up by stable storage.";


      leaf dot1agCfmMdIndex {
        type uint32 {
          range "1..4294967295";
        }
        description 
         "The index to the Maintenance Domain table.
          
          dot1agCfmMdTableNextIndex needs to be inspected to find an
          available index for row-creation.
          
          Referential integrity is required, i.e., the index needs to be
          persistent upon a reboot or restart of a device.  The index
          can never be reused for other Maintenance Domain.  The index
          value SHOULD keep increasing up to the time that they wrap
          around. This is to facilitate access control based on OID.";
      }

      leaf dot1agCfmMdFormat {
        type ieee8021-cfm:Dot1agCfmMaintDomainNameType;
        config true;
        description 
         "The type (and thereby format) of the Maintenance Domain Name.";
        reference   
         "21.6.5.1";
      }

      leaf dot1agCfmMdName {
        type ieee8021-cfm:Dot1agCfmMaintDomainName;
        config true;
        description 
         "The Maintenance Domain name. The type/format of this object
          is determined by the value of the dot1agCfmMdNameType object.
            
          Each Maintenance Domain has unique name amongst all those
          used or available to a service provider or operator.  It
          facilitates easy identification of administrative
          responsibility for each Maintenance Domain.
          
          Clause 3.24 defines a Maintenance Domain name as the
          identifier, unique over the domain for which CFM is to
          protect against accidental concatenation of Service
          Instances, of a particular Maintenance Domain.";
        reference   
         "802.1ag clauses 3.24, 12.14.5, and 21.6.5.3";
      }

      leaf dot1agCfmMdMdLevel {
        type ieee8021-cfm:Dot1agCfmMDLevel;
        config true;
        description 
         "The Maintenance Domain Level.";
        reference   
         "12.14.5.1.3:b";
      }

      leaf dot1agCfmMdMhfCreation {
        type ieee8021-cfm:Dot1agCfmMhfCreation;
        config true;
        description 
         "Enumerated value indicating whether the management entity can
          create MHFs (MIP Half Function) for this Maintenance Domain.
          Since, in this variable, there is no encompassing Maintenance
          Domain, the value defMHFdefer is not allowed.";
        reference   
         "12.14.5.1.3:c";
      }

      leaf dot1agCfmMdMhfIdPermission {
        type ieee8021-cfm:Dot1agCfmIdPermission;
        config true;
        description 
         "Enumerated value indicating what, if anything, is to be
          included in the Sender ID TLV (21.5.3) transmitted by MPs
          configured in this Maintenance Domain.  Since, in this
          variable, there is no encompassing Maintenance Domain, the
          value sendIdDefer is not allowed.";
        reference   
         "12.14.5.1.3:d";
      }

      leaf dot1agCfmMdMaNextIndex {
        type ieee8021-cfm:Dot1afCfmIndexIntegerNextFree;
        description 
         "Value to be used as the index of the MA table entries, both
          the dot1agCfmMaNetTable and the dot1agCfmMaCompTable, for
          this Maintenance Domain when the management entity wants to
          create a new row in those tables.";
      }

      leaf dot1agCfmMdRowStatus {
        type smiv2:RowStatus;
        config true;
        description 
         "The status of the row.
          
          The writable columns in a row can not be changed if the row
          is active. All columns MUST have a valid value before a row
          can be activated.";
      }
    }
  }

  container dot1agCfmMa {


    /* XXX table comments here XXX */

    list dot1agCfmMaNetEntry {

      key "dot1agCfmMdIndex dot1agCfmMaIndex";
      description   
       "The MA table entry.";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }

      leaf dot1agCfmMaIndex {
        type uint32 {
          range "1..4294967295";
        }
        description 
         "Index of the MA table dot1agCfmMdMaNextIndex needs to
          be inspected to find an available index for row-creation.";
      }

      leaf dot1agCfmMaNetFormat {
        type ieee8021-cfm:Dot1agCfmMaintAssocNameType;
        config true;
        description 
         "The type (and thereby format) of the Maintenance Association
          Name.";
        reference   
         "802.1ag clauses 21.6.5.4";
      }

      leaf dot1agCfmMaNetName {
        type ieee8021-cfm:Dot1agCfmMaintAssocName;
        config true;
        description 
         "The Short Maintenance Association name. The type/format of
          this object is determined by the value of the
          dot1agCfmMaNetNameType object.  This name MUST be unique within
          a maintenance domain.";
        reference   
         "802.1ag clauses 21.6.5.6, and Table 21-20";
      }

      leaf dot1agCfmMaNetCcmInterval {
        type ieee8021-cfm:Dot1agCfmCcmInterval;
        config true;
        description 
         "Interval between CCM transmissions to be used by all MEPs
          in the MA.";
        reference   
         "12.14.6.1.3:e";
      }

      leaf dot1agCfmMaNetRowStatus {
        type smiv2:RowStatus;
        config true;
        description 
         "The status of the row.
          
          The writable columns in a row can not be changed if the row
          is active. All columns MUST have a valid value before a row
          can be activated.";
      }
    }


    /* XXX table comments here XXX */

    list dot1agCfmMaCompEntry {

      key "dot1agCfmMaComponentId dot1agCfmMdIndex 
           dot1agCfmMaIndex";
      status deprecated;
      description   
       "The MA table entry.
        **NOTE: this object is deprecated due to re-indexing of the 
        table.";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }

      leaf dot1agCfmMaComponentId {
        type ieee8021-cfm:Dot1agCfmPbbComponentIdentifier;
        status deprecated;
        description 
         "The bridge component within the system to which the information
          in this dot1agCfmMaCompEntry applies.  If the system is not a
          Bridge, or if only one component is present in the Bridge, then
          this variable (index) MUST be equal to 1.
          **NOTE: this object is deprecated due to re-indexing of the 
          table.";
        reference   
         "12.3 l)";
      }

      leaf dot1agCfmMaCompPrimaryVlanId {
        type q-bridge:VlanIdOrNone;
        config true;
        status deprecated;
        description 
         "The Primary VLAN ID with which the Maintenance Association is
          associated, or 0 if the MA is not attached to any VID.  If
          the MA is associated with more than one VID, the
          dot1agCfmVlanTable lists them.
          **NOTE: this object is deprecated due to re-indexing of the 
          table.";
        reference   
         "12.14.6.1.3:b";
      }

      leaf dot1agCfmMaCompMhfCreation {
        type ieee8021-cfm:Dot1agCfmMhfCreation;
        config true;
        status deprecated;
        description 
         "Indicates if the Management entity can create MHFs (MIP Half
          Function) for this MA.
          **NOTE: this object is deprecated due to re-indexing of the 
          table.";
        reference   
         "12.14.6.1.3:c";
      }

      leaf dot1agCfmMaCompIdPermission {
        type ieee8021-cfm:Dot1agCfmIdPermission;
        config true;
        status deprecated;
        description 
         "Enumerated value indicating what, if anything, is to be
          included in the Sender ID TLV (21.5.3) transmitted by MPs
          configured in this MA.
          **NOTE: this object is deprecated due to re-indexing of the 
          table.";
        reference   
         "12.14.6.1.3:d";
      }

      leaf dot1agCfmMaCompNumberOfVids {
        type uint32;
        config true;
        status deprecated;
        description 
         "The number of VIDs associated with the MA.
          **NOTE: this object is deprecated due to re-indexing of the 
          table.";
        reference   
         "12.14.6.1.3:b";
      }

      leaf dot1agCfmMaCompRowStatus {
        type smiv2:RowStatus;
        config true;
        status deprecated;
        description 
         "The status of the row.
          
          The writable columns in a row can not be changed if the row
          is active. All columns MUST have a valid value before a row
          can be activated.
          **NOTE: this object is deprecated due to re-indexing of the 
          table.";
      }
    }


    /* XXX table comments here XXX */

    list dot1agCfmMaMepListEntry {

      key "dot1agCfmMdIndex dot1agCfmMaIndex 
           dot1agCfmMaMepListIdentifier";
      description   
       "The known MEPS table entry.";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }

      leaf dot1agCfmMaMepListIdentifier {
        type ieee8021-cfm:Dot1agCfmMepId;
        description 
         "MEPID";
        reference   
         "12.14.6.1.3:g";
      }

      leaf dot1agCfmMaMepListRowStatus {
        type smiv2:RowStatus;
        config true;
        description 
         "The status of the row. Read SNMPv2-TC (RFC1903) for an
          explanation of the possible values this object can take.";
      }
    }
  }

  container dot1agCfmMep {


    /* XXX table comments here XXX */

    list dot1agCfmMepEntry {

      key "dot1agCfmMdIndex dot1agCfmMaIndex 
           dot1agCfmMepIdentifier";
      description   
       "The MEP table entry";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }

      leaf dot1agCfmMepIdentifier {
        type ieee8021-cfm:Dot1agCfmMepId;
        description 
         "Integer that is unique among all the MEPs in the same MA.
          Other definition is: a small integer, unique over a given
          Maintenance Association, identifying a specific Maintenance
          association End Point (3.19).
          
          MEP Identifier is also known as the MEPID.";
        reference   
         "802.1ag clauses 3.19, 19.2 and 12.14.7";
      }

      leaf dot1agCfmMepIfIndex {
        type if-mib:InterfaceIndexOrZero;
        config true;
        description 
         "This object is the interface index of the interface either a
          bridge port, or an aggregated IEEE 802.1 link within a bridge
          port, to which the MEP is attached.
          
          Upon a restart of the system, the system SHALL, if necessary,
          change the value of this variable so that it indexes the
          entry in the interface table with the same value of ifAlias
          that it indexed before the system restart.  If no such
          entry exists, then the system SHALL set this variable to 0.";
        reference   
         "12.14.7.1.3:b";
      }

      leaf dot1agCfmMepDirection {
        type ieee8021-cfm:Dot1agCfmMpDirection;
        config true;
        description 
         "The direction in which the MEP faces on the Bridge port.";
        reference   
         "802.1ag clauses 12.14.7.1.3:c and 19.2";
      }

      leaf dot1agCfmMepPrimaryVid {
        type uint32 {
          range "0..16777215";
        }
        config true;
        description 
         "An integer indicating the Primary VID of the MEP, always
          one of the VIDs assigned to the MEP's MA.  The value 0
          indicates that either the Primary VID is that of the
          MEP's MA, or that the MEP's MA is associated with no VID.";
        reference   
         "802.1ag clauses 12.14.7.1.3:d";
      }

      leaf dot1agCfmMepActive {
        type smiv2:TruthValue;
        config true;
        description 
         "Administrative state of the MEP
          
          A Boolean indicating the administrative state of the MEP.
          
          True indicates that the MEP is to function normally, and
          false that it is to cease functioning.";
        reference   
         "802.1ag clauses 12.14.7.1.3:e and 20.9.1";
      }

      leaf dot1agCfmMepFngState {
        type ieee8021-cfm:Dot1agCfmFngState;
        description 
         "Current state of the MEP Fault Notification Generator
          State Machine.";
        reference   
         "802.1ag clauses 12.14.7.1.3:f and 20.35";
      }

      leaf dot1agCfmMepCciEnabled {
        type smiv2:TruthValue;
        config true;
        description 
         "If set to true, the MEP will generate CCM messages.";
        reference   
         "802.1ag clauses 12.14.7.1.3:g and 20.10.1";
      }

      leaf dot1agCfmMepCcmLtmPriority {
        type uint32 {
          range "0..7";
        }
        config true;
        description 
         "The priority value for CCMs and LTMs transmitted by the MEP.
          Default Value is the highest priority value allowed to pass
          through the bridge port for any of this MEPs VIDs.
          The management entity can obtain the default value for this 
          variable from the priority regeneration table by extracting the 
          highest priority value in this table on this MEPs bridge port.
          (1 is lowest, then 2, then 0, then 3-7).";
        reference   
         "12.14.7.1.3:h";
      }

      leaf dot1agCfmMepMacAddress {
        type yang:mac-address;
        description 
         "MAC address of the MEP.";
        reference   
         "12.14.7.1.3:i and 19.4";
      }

      leaf dot1agCfmMepLowPrDef {
        type ieee8021-cfm:Dot1agCfmLowestAlarmPri;
        config true;
        description 
         "An integer value specifying the lowest priority defect 
          that is allowed to generate fault alarm.";
        reference   
         "12.14.7.1.3:k and 20.9.5 and Table 20-1";
      }

      leaf dot1agCfmMepFngAlarmTime {
        type smiv2:TimeInterval {
          range "250..1000";
        }
        config true;
        description 
         "The time that defects MUST be present before a Fault Alarm is
          issued (fngAlarmTime. 20.33.3) (default 2.5s).";
        reference   
         "802.1ag clauses 12.14.7.1.3:l and 20.33.3";
      }

      leaf dot1agCfmMepFngResetTime {
        type smiv2:TimeInterval {
          range "250..1000";
        }
        config true;
        description 
         "The time that defects MUST be absent before resetting a
          Fault Alarm (fngResetTime, 20.33.4) (default 10s).";
        reference   
         "802.1ag clauses 12.14.7.1.3:m and 20.33.4";
      }

      leaf dot1agCfmMepHighestPrDefect {
        type ieee8021-cfm:Dot1agCfmHighestDefectPri;
        description 
         "The highest priority defect that has been present since the
          MEPs Fault Notification Generator State Machine was last in
          the FNG_RESET state.";
        reference   
         "12.14.7.1.3:n  20.33.9 and Table 21-1";
      }

      leaf dot1agCfmMepDefects {
        type ieee8021-cfm:Dot1agCfmMepDefects;
        description 
         "A vector of Boolean error conditions from Table 20-1, any of
          which may be true:
          
          DefRDICCM(0)
          DefMACstatus(1)
          DefRemoteCCM(2)
          DefErrorCCM(3)
          DefXconCCM(4)";
        reference   
         ".1ag clauses 12.14.7.1.3:o, 12.14.7.1.3:p, 12.14.7.1.3:q,
          12.14.7.1.3:r, 12.14.7.1.3:s, 20.21.3, 20.23.3, 20.33.5,
          20.33.6, 20.33.7.";
      }

      leaf dot1agCfmMepErrorCcmLastFailure {
        type binary {
          length "1..1522";
        }
        description 
         "The last-received CCM that triggered an DefErrorCCM fault.";
        reference   
         "802.1ag clauses 12.14.7.1.3:t and 20.21.2";
      }

      leaf dot1agCfmMepXconCcmLastFailure {
        type binary {
          length "1..1522";
        }
        description 
         "The last-received CCM that triggered a DefXconCCM fault.";
        reference   
         "802.1ag clauses 12.14.7.1.3:u and 20.23.2";
      }

      leaf dot1agCfmMepCcmSequenceErrors {
        type yang:counter32;
        description 
         "The total number of out-of-sequence CCMs received from all
          remote MEPs.";
        reference   
         "802.1ag clauses 12.14.7.1.3:v and 20.16.12";
      }

      leaf dot1agCfmMepCciSentCcms {
        type yang:counter32;
        description 
         "Total number of Continuity Check messages transmitted.";
        reference   
         "802.1ag clauses 12.14.7.1.3:w and 20.10.2";
      }

      leaf dot1agCfmMepNextLbmTransId {
        type uint32;
        description 
         "Next sequence number/transaction identifier to be sent in a
          Loopback message. This sequence number can be zero because
          it wraps around.";
        reference   
         "802.1ag clauses 12.14.7.1.3:x and 20.28.2";
      }

      leaf dot1agCfmMepLbrIn {
        type yang:counter32;
        description 
         "Total number of valid, in-order Loopback Replies received.";
        reference   
         "12.14.7.1.3:y and 20.31.1";
      }

      leaf dot1agCfmMepLbrInOutOfOrder {
        type yang:counter32;
        description 
         "The total number of valid, out-of-order Loopback Replies
          received.";
        reference   
         "12.14.7.1.3:z and 20.31.1";
      }

      leaf dot1agCfmMepLbrBadMsdu {
        type yang:counter32;
        description 
         "The total number of LBRs received whose
          mac_service_data_unit did not match (except for the OpCode)
          that of the corresponding LBM (20.2.3).";
        reference   
         "12.14.7.1.3:aa  20.2.3";
      }

      leaf dot1agCfmMepLtmNextSeqNumber {
        type uint32;
        description 
         "Next transaction identifier/sequence number to be sent in a
          Linktrace message. This sequence number can be zero because
          it wraps around.";
        reference   
         "12.14.7.1.3:ab and 20.36.1";
      }

      leaf dot1agCfmMepUnexpLtrIn {
        type yang:counter32;
        description 
         "The total number of unexpected LTRs received (20.39.1).";
        reference   
         "12.14.7.1.3:ac  20.39.1";
      }

      leaf dot1agCfmMepLbrOut {
        type yang:counter32;
        description 
         "Total number of Loopback Replies transmitted.";
        reference   
         "12.14.7.1.3:ad and 20.26.2";
      }

      leaf dot1agCfmMepTransmitLbmStatus {
        type smiv2:TruthValue;
        config true;
        description 
         "A Boolean flag set to true by the MEP Loopback Initiator State
          Machine or an MIB manager to indicate
          that another LBM is being transmitted.
          Reset to false by the MEP Loopback Initiator State Machine.";
      }

      leaf dot1agCfmMepTransmitLbmDestMacAddress {
        type yang:mac-address;
        config true;
        description 
         "The Target MAC Address Field to be transmitted: A unicast
          destination MAC address.
          This address will be used if the value of the column
          dot1agCfmMepTransmitLbmDestIsMepId is 'false'.";
        reference   
         "12.14.7.3.2:b";
      }

      leaf dot1agCfmMepTransmitLbmDestMepId {
        type ieee8021-cfm:Dot1agCfmMepIdOrZero;
        config true;
        description 
         "The Maintenance association End Point Identifier of another
          MEP in the same Maintenance Association to which the LBM is
          to be sent.
          This address will be used if the value of the column
          dot1agCfmMepTransmitLbmDestIsMepId is 'true'.";
        reference   
         "12.14.7.3.2:b";
      }

      leaf dot1agCfmMepTransmitLbmDestIsMepId {
        type smiv2:TruthValue;
        config true;
        description 
         "True indicates that MEPID of the target MEP is used for
          Loopback transmission.
          False indicates that unicast destination MAC address of the
          target MEP is used for Loopback transmission.";
        reference   
         "12.14.7.3.2:b";
      }

      leaf dot1agCfmMepTransmitLbmMessages {
        type int32 {
          range "1..1024";
        }
        config true;
        description 
         "The number of Loopback messages to be transmitted.";
        reference   
         "12.14.7.3.2:c";
      }

      leaf dot1agCfmMepTransmitLbmDataTlv {
        type binary;
        config true;
        description 
         "An arbitrary amount of data to be included in the Data TLV,
          if the Data TLV is selected to be sent.  The intent is to be able
          to fill the frame carrying the CFM PDU to its maximum length.
          This may lead to fragmentation in some cases.";
        reference   
         "12.14.7.3.2:d";
      }

      leaf dot1agCfmMepTransmitLbmVlanPriority {
        type int32 {
          range "0..7";
        }
        config true;
        description 
         "Priority. 3 bit value to be used in the VLAN tag, if present
          in the transmitted frame.
          
          The default value is CCM priority.";
        reference   
         "12.14.7.3.2:e";
      }

      leaf dot1agCfmMepTransmitLbmVlanDropEnable {
        type smiv2:TruthValue;
        config true;
        description 
         "Drop Enable bit value to be used in the VLAN tag, if present
          in the transmitted frame.
          
          For more information about VLAN Drop Enable, please check
          IEEE 802.1ad.";
        reference   
         "12.14.7.3.2:e";
      }

      leaf dot1agCfmMepTransmitLbmResultOK {
        type smiv2:TruthValue;
        description 
         "Indicates the result of the operation:
          
          - true       The Loopback Message(s) will be
                       (or has been) sent.
          - false      The Loopback Message(s) will not
                       be sent.";
        reference   
         "12.14.7.3.3:a";
      }

      leaf dot1agCfmMepTransmitLbmSeqNumber {
        type uint32;
        description 
         "The Loopback Transaction Identifier
          (dot1agCfmMepNextLbmTransId) of the first LBM (to be) sent.
           The value returned is undefined if
           dot1agCfmMepTransmitLbmResultOK is false.";
        reference   
         "12.14.7.3.3:a";
      }

      leaf dot1agCfmMepTransmitLtmStatus {
        type smiv2:TruthValue;
        config true;
        description 
         "A Boolean flag set to true by the bridge port to indicate
          that another LTM may be transmitted. 
          Reset to false by the MEP Linktrace Initiator State Machine.";
      }

      leaf dot1agCfmMepTransmitLtmFlags {
        type bits {
          bit useFDBonly { position 0; }
        }
        config true;
        description 
         "The flags field for LTMs transmitted by the MEP.";
        reference   
         "12.14.7.4.2:b and 20.37.1";
      }

      leaf dot1agCfmMepTransmitLtmTargetMacAddress {
        type yang:mac-address;
        config true;
        description 
         "The Target MAC Address Field to be transmitted: A unicast
          destination MAC address.
          This address will be used if the value of the column
          dot1agCfmMepTransmitLtmTargetIsMepId is 'false'.";
        reference   
         "12.14.7.4.2:c";
      }

      leaf dot1agCfmMepTransmitLtmTargetMepId {
        type ieee8021-cfm:Dot1agCfmMepIdOrZero;
        config true;
        description 
         "An indication of the Target MAC Address Field to be
          transmitted:
          The Maintenance association End Point Identifier of
          another MEP in the same Maintenance Association
          This address will be used if the value of the column
          dot1agCfmMepTransmitLtmTargetIsMepId is 'true'.";
        reference   
         "12.14.7.4.2:c";
      }

      leaf dot1agCfmMepTransmitLtmTargetIsMepId {
        type smiv2:TruthValue;
        config true;
        description 
         "True indicates that MEPID of the target MEP is used for
          Linktrace transmission.
          False indicates that unicast destination MAC address of the
          target MEP is used for Loopback transmission.";
        reference   
         "12.14.7.4.2:c";
      }

      leaf dot1agCfmMepTransmitLtmTtl {
        type uint32 {
          range "0..255";
        }
        config true;
        description 
         "The LTM TTL field. Default value, if not specified, is 64.
          The TTL field indicates the number of hops remaining to the
          LTM.  Decremented by 1 by each Linktrace Responder that
          handles the LTM.  The value returned in the LTR is one less
          than that received in the LTM.  If the LTM TTL is 0 or 1, the
          LTM is not forwarded to the next hop, and if 0, no LTR is
          generated.";
        reference   
         "12.14.7.4.2:d and 21.8.4";
      }

      leaf dot1agCfmMepTransmitLtmResult {
        type smiv2:TruthValue;
        description 
         "Indicates the result of the operation:
          
          - true    The Linktrace Message will be (or has been) sent.
          - false   The Linktrace Message will not be sent";
        reference   
         "12.14.7.4.3:a";
      }

      leaf dot1agCfmMepTransmitLtmSeqNumber {
        type uint32;
        description 
         "The LTM Transaction Identifier
          (dot1agCfmMepLtmNextSeqNumber) of the LTM sent.
          The value returned is undefined if
          dot1agCfmMepTransmitLtmResult is false.";
        reference   
         "12.14.7.4.3:a";
      }

      leaf dot1agCfmMepTransmitLtmEgressIdentifier {
        type binary {
          length "8";
        }
        config true;
        description 
         "Identifies the MEP Linktrace Initiator that is originating,
          or the Linktrace Responder that is forwarding, this LTM.
          The low-order six octets contain a 48-bit IEEE MAC address
          unique to the system in which the MEP Linktrace Initiator
          or Linktrace Responder resides.  The high-order two octets
          contain a value sufficient to uniquely identify the MEP
          Linktrace Initiator or Linktrace Responder within that system.
          
          For most Bridges, the address of any MAC attached to the
          Bridge will suffice for the low-order six octets, and 0 for
          the high-order octets.  In some situations, e.g., if multiple
          virtual Bridges utilizing emulated LANs are implemented in a
          single physical system, the high-order two octets can be used
          to differentiate among the transmitting entities.
          
          The value returned is undefined if
          dot1agCfmMepTransmitLtmResult is false.";
        reference   
         "12.14.7.4.3:b and 21.8.8";
      }

      leaf dot1agCfmMepRowStatus {
        type smiv2:RowStatus;
        config true;
        description 
         "The status of the row.
          
          The writable columns in a row can not be changed if the row
          is active. All columns MUST have a valid value before a row
          can be activated.";
      }

      leaf dot1agCfmMepPbbTeCanReportPbbTePresence {
        type smiv2:TruthValue;
        config true;
        description 
         "A Boolean valued parameter that is set to true if the system
          has the capability to report the presence of traffic and that
          the capability is enabled. Traffic presence reporting is an
          optional PBB-TE feature.";
        reference   
         "12.14.7.1.3:af and 21.6.1.4";
      }

      leaf dot1agCfmMepPbbTeTrafficMismatchDefect {
        type smiv2:TruthValue;
        description 
         "A Boolean valued parameter that is set to true if the system
          has detected a traffic field mismatch defect.  Mismatch detection
           is an optional PBB-TE feature.";
        reference   
         "12.14.7.1.3:ah and 21.6.1.4";
      }

      leaf dot1agCfmMepPbbTransmitLbmLtmReverseVid {
        type ieee8021-tc:IEEE8021VlanIndex;
        config true;
        description 
         "This column specifies the value to use in the Reverse VID value
          field of PBB-TE MIP TLVs contained within TransmitLTM pdus.";
        reference   
         "12.14.7.4.2";
      }

      leaf dot1agCfmMepPbbTeMismatchAlarm {
        type smiv2:TruthValue;
        config true;
        description 
         "A Boolean valued parameter that is set to true if the system
          is to allow a mismatch defect to generate a fault alarm.";
        reference   
         "12.14.7.1.3:ag and 21.6.1.4";
      }

      leaf dot1agCfmMepPbbTeLocalMismatchDefect {
        type smiv2:TruthValue;
        description 
         "A Boolean valued parameter that is set to true if the system
          has detected a local mismatch defect.  Mismatch detection
          is an optional PBB-TE feature.";
        reference   
         "12.14.7.1.3:ai and 21.6.1.4";
      }

      leaf dot1agCfmMepPbbTeMismatchSinceReset {
        type smiv2:TruthValue;
        description 
         "A Boolean valued parameter indicating if the mismatch defect
          has been present since the MEP Mismatch Fault Notification
          Generator was last in the MFNG_RESET state.";
        reference   
         "12.14.7.1.3:aj";
      }
    }


    /* XXX table comments here XXX */

    list dot1agCfmLtrEntry {

      key "dot1agCfmMdIndex dot1agCfmMaIndex 
           dot1agCfmMepIdentifier dot1agCfmLtrSeqNumber 
           dot1agCfmLtrReceiveOrder";
      description   
       "The Linktrace Reply table entry.";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }

      leaf dot1agCfmLtrSeqNumber {
        type uint32 {
          range "0..4294967295";
        }
        description 
         "Transaction identifier/Sequence number returned by a previous
          transmit linktrace message command, indicating which LTM's
          response is going to be returned.";
        reference   
         "12.14.7.5.2:b";
      }

      leaf dot1agCfmLtrReceiveOrder {
        type uint32 {
          range "1..4294967295";
        }
        description 
         "An index to distinguish among multiple LTRs with the same LTR
          Transaction Identifier field value.  dot1agCfmLtrReceiveOrder
          are assigned sequentially from 1, in the order that the
          Linktrace Initiator received the LTRs.";
        reference   
         "12.14.7.5.2:c";
      }

      leaf dot1agCfmLtrTtl {
        type uint32 {
          range "0..255";
        }
        description 
         "TTL field value for a returned LTR.";
        reference   
         "12.14.7.5 and 20.36.2.2";
      }

      leaf dot1agCfmLtrForwarded {
        type smiv2:TruthValue;
        description 
         "Indicates if a LTM was forwarded by the responding MP, as
          returned in the 'FwdYes' flag of the flags field.";
        reference   
         "802.1ag clauses 12.14.7.5.3:c and 20.36.2.1";
      }

      leaf dot1agCfmLtrTerminalMep {
        type smiv2:TruthValue;
        description 
         "A Boolean value stating whether the forwarded LTM reached a
          MEP enclosing its MA, as returned in the Terminal MEP flag of
          the Flags field.";
        reference   
         "802.1ag clauses 12.14.7.5.3:d and 20.36.2.1";
      }

      leaf dot1agCfmLtrLastEgressIdentifier {
        type binary {
          length "8";
        }
        description 
         "An octet field holding the Last Egress Identifier returned
          in the LTR Egress Identifier TLV of the LTR.
          The Last Egress Identifier identifies the MEP Linktrace 
          Initiator that originated, or the Linktrace Responder that 
          forwarded, the LTM to which this LTR is the response.  This
          is the same value as the Egress Identifier TLV of that LTM.";
        reference   
         "802.1ag clauses 12.14.7.5.3:e and 20.36.2.3";
      }

      leaf dot1agCfmLtrNextEgressIdentifier {
        type binary {
          length "8";
        }
        description 
         "An octet field holding the Next Egress Identifier returned
          in the LTR Egress Identifier TLV of the LTR.  The Next Egress
          Identifier Identifies the Linktrace Responder that
          transmitted this LTR, and can forward the LTM to the next
          hop.  This is the same value as the Egress Identifier TLV of
          the forwarded LTM, if any. If the FwdYes bit of the Flags
          field is false, the contents of this field are undefined,
          i.e., any value can be transmitted, and the field is ignored
          by the receiver.";
        reference   
         "802.1ag clauses 12.14.7.5.3:f and 20.36.2.4";
      }

      leaf dot1agCfmLtrRelay {
        type ieee8021-cfm:Dot1agCfmRelayActionFieldValue;
        description 
         "Value returned in the Relay Action field.";
        reference   
         "802.1ag clauses 12.14.7.5.3:g and 20.36.2.5";
      }

      leaf dot1agCfmLtrChassisIdSubtype {
        type lldp-mib:LldpChassisIdSubtype;
        description 
         "This object specifies the format of the Chassis ID returned
          in the Sender ID TLV of the LTR, if any.  This value is
          meaningless if the dot1agCfmLtrChassisId has a length of 0.";
        reference   
         "802.1ag clauses 12.14.7.5.3:h and 21.5.3.2";
      }

      leaf dot1agCfmLtrChassisId {
        type lldp-mib:LldpChassisId;
        description 
         "The Chassis ID returned in the Sender ID TLV of the LTR, if
          any. The format of this object is determined by the
          value of the dot1agCfmLtrChassisIdSubtype object.";
        reference   
         "802.1ag clauses 12.14.7.5.3:i and 21.5.3.3";
      }

      leaf dot1agCfmLtrManAddressDomain {
        type smiv2:TDomain;
        description 
         "The TDomain that identifies the type and format of
          the related dot1agCfmMepDbManAddress object, used to access
          the SNMP agent of the system transmitting the LTR.  Received
          in the LTR Sender ID TLV from that system.
          
          Typical values will be one of (not all inclusive) list:
          
          
             snmpUDPDomain          (from SNMPv2-TM, RFC3417)
             snmpIeee802Domain      (from SNMP-IEEE802-TM-MIB, RFC4789)
          
          The value 'zeroDotZero' (from RFC2578) indicates 'no management
          address was present in the LTR', in which case the related
          object dot1agCfmMepDbManAddress MUST have a zero-length OCTET
          STRING as a value.";
        reference   
         "802.1ag clauses 12.14.7.5.3:j, 21.5.3.5, 21.9.6";
      }

      leaf dot1agCfmLtrManAddress {
        type smiv2:TAddress;
        description 
         "The TAddress that can be used to access the SNMP
          agent of the system transmitting the CCM, received in the CCM
          Sender ID TLV from that system.
          
          If the related object dot1agCfmLtrManAddressDomain contains
          the value 'zeroDotZero', this object dot1agCfmLtrManAddress
          MUST have a zero-length OCTET STRING as a value.";
        reference   
         "802.1ag clauses 12.14.7.5.3:j, 21.5.3.7, 21.9.6";
      }

      leaf dot1agCfmLtrIngress {
        type ieee8021-cfm:Dot1agCfmIngressActionFieldValue;
        description 
         "The value returned in the Ingress Action Field of the LTM.
          The value ingNoTlv(0) indicates that no Reply Ingress TLV was
          returned in the LTM.";
        reference   
         "802.1ag clauses 12.14.7.5.3:k and 20.36.2.6";
      }

      leaf dot1agCfmLtrIngressMac {
        type yang:mac-address;
        description 
         "MAC address returned in the ingress MAC address field.
          If the dot1agCfmLtrIngress object contains the value
          ingNoTlv(0), then the contents of this object are meaningless.";
        reference   
         "802.1ag clauses 12.14.7.5.3:l and 20.36.2.7";
      }

      leaf dot1agCfmLtrIngressPortIdSubtype {
        type lldp-mib:LldpPortIdSubtype;
        description 
         "Format of the Ingress Port ID.
          If the dot1agCfmLtrIngress object contains the value
          ingNoTlv(0), then the contents of this object are meaningless.";
        reference   
         "802.1ag clauses 12.14.7.5.3:m and 20.36.2.8";
      }

      leaf dot1agCfmLtrIngressPortId {
        type lldp-mib:LldpPortId;
        description 
         "Ingress Port ID. The format of this object is determined by
          the value of the dot1agCfmLtrIngressPortIdSubtype object.
          If the dot1agCfmLtrIngress object contains the value
          ingNoTlv(0), then the contents of this object are meaningless.";
        reference   
         "802.1ag clauses 12.14.7.5.3:n and 20.36.2.9";
      }

      leaf dot1agCfmLtrEgress {
        type ieee8021-cfm:Dot1agCfmEgressActionFieldValue;
        description 
         "The value returned in the Egress Action Field of the LTM.
          The value egrNoTlv(0) indicates that no Reply Egress TLV was
          returned in the LTM.";
        reference   
         "802.1ag clauses 12.14.7.5.3:o and 20.36.2.10";
      }

      leaf dot1agCfmLtrEgressMac {
        type yang:mac-address;
        description 
         "MAC address returned in the egress MAC address field.
          If the dot1agCfmLtrEgress object contains the value
          egrNoTlv(0), then the contents of this object are meaningless.";
        reference   
         "802.1ag clauses 12.14.7.5.3:p and 20.36.2.11";
      }

      leaf dot1agCfmLtrEgressPortIdSubtype {
        type lldp-mib:LldpPortIdSubtype;
        description 
         "Format of the egress Port ID.
          If the dot1agCfmLtrEgress object contains the value
          egrNoTlv(0), then the contents of this object are meaningless.";
        reference   
         "802.1ag clauses 12.14.7.5.3:q and 20.36.2.12";
      }

      leaf dot1agCfmLtrEgressPortId {
        type lldp-mib:LldpPortId;
        description 
         "Egress Port ID. The format of this object is determined by
          the value of the dot1agCfmLtrEgressPortIdSubtype object.
          If the dot1agCfmLtrEgress object contains the value
          egrNoTlv(0), then the contents of this object are meaningless.";
        reference   
         "802.1ag clauses 12.14.7.5.3:r and 20.36.2.13";
      }

      leaf dot1agCfmLtrOrganizationSpecificTlv {
        type binary {
          length "0 | 4..1500";
        }
        description 
         "All Organization specific TLVs returned in the LTR, if
          any.  Includes all octets including and following the TLV
          Length field of each TLV, concatenated together.";
        reference   
         "802.1ag clauses 12.14.7.5.3:s, 21.5.2";
      }
    }


    /* XXX table comments here XXX */

    list dot1agCfmMepDbEntry {

      key "dot1agCfmMdIndex dot1agCfmMaIndex 
           dot1agCfmMepIdentifier dot1agCfmMepDbRMepIdentifier";
      description   
       "The MEP Database table entry.";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }

      leaf dot1agCfmMepDbRMepIdentifier {
        type ieee8021-cfm:Dot1agCfmMepId;
        description 
         "Maintenance association End Point Identifier of a remote MEP
          whose information from the MEP Database is to be returned.";
        reference   
         "12.14.7.6.2:b";
      }

      leaf dot1agCfmMepDbRMepState {
        type ieee8021-cfm:Dot1agCfmRemoteMepState;
        description 
         "The operational state of the remote MEP IFF State machines.";
        reference   
         "12.14.7.6.3:b and 20.22";
      }

      leaf dot1agCfmMepDbRMepFailedOkTime {
        type yang:timestamp;
        description 
         "The time (SysUpTime) at which the IFF Remote MEP state machine
          last entered either the RMEP_FAILED or RMEP_OK state.";
        reference   
         "12.14.7.6.3:c";
      }

      leaf dot1agCfmMepDbMacAddress {
        type yang:mac-address;
        description 
         "The MAC address of the remote MEP.";
        reference   
         "12.14.7.6.3:d and 20.19.7";
      }

      leaf dot1agCfmMepDbRdi {
        type smiv2:TruthValue;
        description 
         "State of the RDI bit in the last received CCM (true for
          RDI=1), or false if none has been received.";
        reference   
         "802.1ag clauses 12.14.7.6.3:e and 20.19.2";
      }

      leaf dot1agCfmMepDbPortStatusTlv {
        type ieee8021-cfm:Dot1agCfmPortStatus;
        description 
         "An enumerated value of the Port status TLV received in the
          last CCM from the remote MEP or the default value
          psNoPortStateTLV indicating either no CCM has been received,
          or that nor port status TLV was received in the last CCM.";
        reference   
         "12.14.7.6.3:f and 20.19.3";
      }

      leaf dot1agCfmMepDbInterfaceStatusTlv {
        type ieee8021-cfm:Dot1agCfmInterfaceStatus;
        description 
         "An enumerated value of the Interface status TLV received
          in the last CCM from the remote MEP or the default value
          isNoInterfaceStatus TLV indicating either no CCM has been
          received, or that no interface status TLV was received in
          the last CCM.";
        reference   
         "12.14.7.6.3:g and 20.19.4";
      }

      leaf dot1agCfmMepDbChassisIdSubtype {
        type lldp-mib:LldpChassisIdSubtype;
        description 
         "This object specifies the format of the Chassis ID received
          in the last CCM.";
        reference   
         "802.1ag clauses 12.14.7.6.3:h and 21.5.3.2";
      }

      leaf dot1agCfmMepDbChassisId {
        type lldp-mib:LldpChassisId;
        description 
         "The Chassis ID. The format of this object is determined by the
          value of the dot1agCfmLtrChassisIdSubtype object.";
        reference   
         "802.1ag clauses 12.14.7.6.3:h and 21.5.3.3";
      }

      leaf dot1agCfmMepDbManAddressDomain {
        type smiv2:TDomain;
        description 
         "The TDomain that identifies the type and format of
          the related dot1agCfmMepDbManAddress object, used to access
          the SNMP agent of the system transmitting the CCM.  Received
          in the CCM Sender ID TLV from that system.
          
          Typical values will be one of (not all inclusive) list:
          
          
             snmpUDPDomain          (from SNMPv2-TM, RFC3417)
             snmpIeee802Domain      (from SNMP-IEEE802-TM-MIB, RFC4789)
          
          The value 'zeroDotZero' (from RFC2578) indicates 'no management
          address was present in the LTR', in which case the related
          object dot1agCfmMepDbManAddress MUST have a zero-length OCTET
          STRING as a value.";
        reference   
         "802.1ag clauses 12.14.7.6.3:h, 21.5.3.5, 21.6.7";
      }

      leaf dot1agCfmMepDbManAddress {
        type smiv2:TAddress;
        description 
         "The TAddress that can be used to access the SNMP
          agent of the system transmitting the CCM, received in the CCM
          Sender ID TLV from that system.
          
          If the related object dot1agCfmMepDbManAddressDomain contains
          the value 'zeroDotZero', this object dot1agCfmMepDbManAddress
          MUST have a zero-length OCTET STRING as a value.";
        reference   
         "802.1ag clauses 12.14.7.6.3:h, 21.5.3.7, 21.6.7";
      }

      leaf dot1agCfmMepDbRMepIsActive {
        type smiv2:TruthValue;
        config true;
        description 
         "A Boolean value stating if the remote MEP is active.";
        reference   
         "12.14.7.1.3:af";
      }
    }
  }

  notification dot1agCfmFaultAlarm {
    description     
     "A MEP has a persistent defect condition. A notification
      (fault alarm) is sent to the management entity with the OID
      of the MEP that has detected the fault.
      
      Whenever a MEP has a persistent defect,
      it may or may not generate a Fault Alarm to warn the system
      administrator of the problem, as controlled by the MEP
      Fault Notification Generator State Machine and associated
      Managed Objects. Only the highest-priority defect, as shown
      in Table 20-1, is reported in the Fault Alarm.
      
      If a defect with a higher priority is raised after a Fault
      Alarm has been issued, another Fault Alarm is issued.
      
      The management entity receiving the notification can identify
      the system from the network source address of the
      notification, and can identify the MEP reporting the defect
      by the indices in the OID of the dot1agCfmMepHighestPrDefect
      variable in the notification:
      
         dot1agCfmMdIndex - Also the index of the MEP's
                            Maintenance Domain table entry
                            (dot1agCfmMdTable).
         dot1agCfmMaIndex - Also an index (with the MD table index)
                            of the MEP's Maintenance Association
                            network table entry
                            (dot1agCfmMaNetTable), and (with the MD
                            table index and component ID) of the
                            MEP's MA component table entry
                            (dot1agCfmMaCompTable).
         dot1agCfmMepIdentifier - MEP Identifier and final index
                            into the MEP table (dot1agCfmMepTable).";
    reference       
     "12.14.7.7";

    container dot1agCfmFaultAlarm-dot1agCfmMepHighestPrDefect {
      leaf dot1agCfmMdIndex {
        type leafref {
          path "/ieee8021-cfm:dot1agCfmMd/ieee8021-cfm:dot1agCfmMdEntry/ieee8021-cfm:dot1agCfmMdIndex";
        }
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        description 
         "Automagically generated leafref leaf.";
      }
      leaf dot1agCfmMepHighestPrDefect {
        type ieee8021-cfm:Dot1agCfmHighestDefectPri;
        description 
         "The highest priority defect that has been present since the
          MEPs Fault Notification Generator State Machine was last in
          the FNG_RESET state.";
        reference   
         "12.14.7.1.3:n  20.33.9 and Table 21-1";
      }
    }

  }
} /* end of module IEEE8021-CFM-MIB */
