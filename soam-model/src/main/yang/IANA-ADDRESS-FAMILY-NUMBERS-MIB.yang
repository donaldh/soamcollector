/*
 * This module has been generated by smidump 0.4.8:
 *
 *      smidump -f yang IANA-ADDRESS-FAMILY-NUMBERS-MIB
 *
 * Do not edit. Edit the source file instead!
 */

module IANA-ADDRESS-FAMILY-NUMBERS-MIB {

  /*** NAMESPACE / PREFIX DEFINITION ***/

  namespace "urn:ietf:params:xml:ns:yang:smiv2:IANA-ADDRESS-FAMILY-NUMBERS-MIB";
  prefix "iana-address";

  /*** LINKAGE (IMPORTS / INCLUDES) ***/


  /*** META INFORMATION ***/

  organization      
   "IANA";

  contact           
   "Postal:    Internet Assigned Numbers Authority
    Internet Corporation for Assigned Names
     and Numbers
    4676 Admiralty Way, Suite 330
    Marina del Rey, CA 90292-6601
    USA
    
    Tel:    +1  310-823-9358
    E-Mail: iana&iana.org";

  description       
   "The MIB module defines the AddressFamilyNumbers
    textual convention.";

  revision "2002-03-14" {
    description     
     "AddressFamilyNumbers assignment 22 to 
      fibreChannelWWPN. AddressFamilyNumbers 
      assignment 23 to fibreChannelWWNN.
      AddressFamilyNumers assignment 24 to gwid.";
  }
  revision "2000-09-08" {
    description     
     "AddressFamilyNumbers assignment 19 to xtpOverIpv4.  
      AddressFamilyNumbers assignment 20 to xtpOverIpv6.  
      AddressFamilyNumbers assignment 21 to xtpNativeModeXTP.";
  }
  revision "2000-03-01" {
    description     
     "AddressFamilyNumbers assignment 17 to distinguishedName. 
      AddressFamilyNumbers assignment 18 to asNumber.";
  }
  revision "2000-02-04" {
    description     
     "AddressFamilyNumbers assignment 16 to dns.";
  }
  revision "1999-08-26" {
    description     
     "Initial version, published as RFC 2677.";
  }

  /*** TYPE DEFINITIONS ***/

  typedef AddressFamilyNumbers {
    type enumeration {
      enum other             { value 0; }
      enum ipV4              { value 1; }
      enum ipV6              { value 2; }
      enum nsap              { value 3; }
      enum hdlc              { value 4; }
      enum bbn1822           { value 5; }
      enum all802            { value 6; }
      enum e163              { value 7; }
      enum e164              { value 8; }
      enum f69               { value 9; }
      enum x121              { value 10; }
      enum ipx               { value 11; }
      enum appleTalk         { value 12; }
      enum decnetIV          { value 13; }
      enum banyanVines       { value 14; }
      enum e164withNsap      { value 15; }
      enum dns               { value 16; }
      enum distinguishedName { value 17; }
      enum asNumber          { value 18; }
      enum xtpOverIpv4       { value 19; }
      enum xtpOverIpv6       { value 20; }
      enum xtpNativeModeXTP  { value 21; }
      enum fibreChannelWWPN  { value 22; }
      enum fibreChannelWWNN  { value 23; }
      enum gwid              { value 24; }
      enum afi               { value 25; }
      enum reserved          { value 65535; }
    }
    description     
     "The definition of this textual convention with the
      addition of newly assigned values is published
      periodically by the IANA, in either the Assigned
      Numbers RFC, or some derivative of it specific to
      Internet Network Management number assignments.
      (The latest arrangements can be obtained by
      contacting the IANA.)
      
      The enumerations are described as:
      
      other(0),    -- none of the following
      ipV4(1),     -- IP Version 4
      ipV6(2),     -- IP Version 6
      nsap(3),     -- NSAP
      hdlc(4),     -- (8-bit multidrop)
      bbn1822(5),
      all802(6),   -- (includes all 802 media
                   --   plus Ethernet 'canonical format')
      e163(7),
      e164(8),     -- (SMDS, Frame Relay, ATM)
      f69(9),      -- (Telex)
      x121(10),    -- (X.25, Frame Relay)
      ipx(11),     -- IPX (Internet Protocol Exchange)
      appleTalk(12),  -- Apple Talk
      decnetIV(13),   -- DEC Net Phase IV
      banyanVines(14),  -- Banyan Vines
      e164withNsap(15),
                   -- (E.164 with NSAP format subaddress)
      dns(16),     -- (Domain Name System)
      distinguishedName(17), -- (Distinguished Name, per X.500)
      asNumber(18), -- (16-bit quantity, per the AS number space)
      xtpOverIpv4(19),  -- XTP over IP version 4
      xtpOverIpv6(20),  -- XTP over IP version 6
      xtpNativeModeXTP(21),  -- XTP native mode XTP
      fibreChannelWWPN(22),  -- Fibre Channel World-Wide Port Name 
      fibreChannelWWNN(23),  -- Fibre Channel World-Wide Node Name
      gwid(24),    -- Gateway Identifier 
      afi(25),  -- AFI for L2VPN information
      reserved(65535)
      
      
      
      Requests for new values should be made to IANA via
      email (iana&iana.org).";
  }

} /* end of module IANA-ADDRESS-FAMILY-NUMBERS-MIB */
