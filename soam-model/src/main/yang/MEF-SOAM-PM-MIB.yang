/*
 * This module has been generated by smidump 0.4.8:
 *
 *      smidump -f yang MEF-SOAM-PM-MIB
 *
 * Do not edit. Edit the source file instead!
 */

module MEF-SOAM-PM-MIB {

  /*** NAMESPACE / PREFIX DEFINITION ***/

  namespace "urn:ietf:params:xml:ns:yang:smiv2:MEF-SOAM-PM-MIB";
  prefix "mef-soam-pm";

  /*** LINKAGE (IMPORTS / INCLUDES) ***/

  import IEEE8021-CFM-MIB { prefix "ieee8021-cfm"; }
  import IEEE8021-TC-MIB  { prefix "ieee8021-tc"; }
  import MEF-SOAM-TC-MIB  { prefix "mef-soam"; }
  import SNMPv2-TC        { prefix "smiv2"; }
  import ietf-yang-types       { prefix "yang"; }

  /*** META INFORMATION ***/

  organization      
   "Metro Ethernet Forum";

  contact           
   "Web URL: http://metroethernetforum.org/
    E-mail:  mibs@metroethernetforum.org
    Postal:  Metro Ethernet Forum
             6033 W. Century Boulevard, Suite 830
             Los Angeles, CA 90045
             U.S.A.
    Phone:   +1 310-642-2800
    Fax:     +1 310-642-2808";

  description       
   "This MIB module contains the management objects for the
    management of Ethernet Services Operations, Administration
    and Maintenance for Performance Monitoring.
    
    Copyright 2010, 2011, 2012 Metro Ethernet Forum
    All rights reserved.
    
    ****************************************************************************
    Reference Overview
    
    A number of base documents have been used to create the Textual Conventions
    MIB, the SOAM-PM MIB and SOAM-FM extension MIB. The following are the 
    abbreviations for the baseline documents:
    
    [CFM] refers to 'Connectivity Fault Management', IEEE 802.1ag-2007, 
    December 2007
    [MEF7.1] refers to MEF 7.1 'Phase 2 EMS-NMS Information Model', 
    October 2009
    [MEF17] refers to MEF 17 'Service OAM Requirements & Framework - Phase 1',
    April 2007
    [MEF10.2.1] refers to MEF 10.2.1 'Ethernet Services Attributes Phase 2', 
    January 2011
    [MEF SOAM-PM] refers to MEF 35 'Service OAM Performance Monitoring
    Implementation Agreement', January 2012
    [MEF SOAM-FM] refers to MEF 30 'Service OAM Fault Management Implementation
    Agreement', January 2011
    [Q.840.1] refers to 'ITU-T Requirements and analysis for NMS-EMS
    management interface of Ethernet over Transport and Metro Ethernet
    Network (EoT/MEN)', March 2007
    [Y.1731] refers to ITU-T Y.1731 'OAM functions and mechanisms for Ethernet 
    based networks', February 2011
    ****************************************************************************
    
    Abbreviations Used 
    
    Term         Definition
    Availability Performance   A measure of the percentage of time within a
        specified time interval during which the frame loss is small 
    Backward     OAM information sent from the Responder MEP to the Controller MEP. For
        LM it indicates the frame counts/loss from the Responder MEP to the
        Controller MEP. For DM is indicates the delay and delay variation
        from the Responder MEP to the Controller MEP. 
    BSS          Business Support System
    CCM          Continuity Check Message
    CFM          Connectivity Fault Management 
    CHLI         Consecutive High Loss Interval, a sequence of small time  intervals
     contained in T, each with high frame loss ratio
    Controller MEP   The Controller MEP initiates SOAM PDUs, and receives responses
        from the Responder MEP. 
    CoS          Class of Service 
    DM           Delay Measurement
    Dual-Ended   A type of process where a MEP sends measurement information to a peer
        MEP that will perform the calculations.
    EMS          Element Management System
    ETH-DM       Ethernet Delay Measurement function 
    ETH-LM       Ethernet Loss Measurement function 
    ETH-SLM      Ethernet Synthetic Frame Loss Measurement function 
    EVC          Ethernet Virtual Connection 
    FD           Frame Delay 
    FDR          Frame Delay Range 
    FLR          Frame Loss Ratio 
    FM           Fault Management 
    Forward      OAM information sent from the Controller MEP to the Responder MEP.
       For LM it indicates the frame counts/loss from the Controller MEP
       to the Responder MEP. For DM is indicates the delay and delay
       variation from the Controller MEP to the Responder MEP. 
    HLI          High Loss Interval, a small time interval contained in T with a
        high frame loss ratio 
    IEEE         Institute of Electrical and Electronics Engineers
    IETF         Internet Engineering Task Force
    IFDV         Inter-Frame Delay Variation 
    ITU-T        International Telecommunication Union - Telecommunication
        Standardization Bureau
    LAN          Local Area Network 
    LM           Loss Measurement 
    MAC          Media Access Control 
    MA           Maintenance Association (equivalent to a MEG) 
    MD           Maintenance Domain (equivalent to a OAM Domain in MEF 17) 
    MD Level     Maintenance Domain Level (equivalent to a MEG level) 
    ME           Maintenance Entity 
    Measurement Bin   A Measurement Bin is a counter that stores the number of
        performance measurements falling within a specified range, during
        a Measurement Interval 
    Measurement Interval   A period of time during which measurements are taken.
       Measurements initiated during one Measurement Interval are kept
       separate from measurements taken during other Measurement Intervals.
       It is important to note that this is different from T.
    MEF         Metro Ethernet Forum
    MEG         Maintenance Entity Group (equivalent to a MA) 
    MEG Level   Maintenance Entity Group Level (equivalent to MD Level) 
    MEN         Metro Ethernet Network 
    MEP         Maintenance Association End Point or MEG End Point 
    MFD         Mean Frame Delay 
    MIB         Management Information Base 
    MIP         Maintenance Domain Intermediate Point or MEG Intermediate Point 
    MP          Maintenance Point. One of either a MEP or a MIP 
    NE          Network Element 
    NMS         Network Management System 
    OAM         Operations, Administration, and Maintenance On-Demand   OAM actions that are initiated via manual intervention for a limited
       time to carry out diagnostics.  On-Demand OAM can result in
       singular or periodic OAM actions during the diagnostic time
       interval 
    One-way     A measurement performed in the forward or backward direction. For
       example from MEP A to MEP B or from MEP B to MEP A. 
    OSS         Operations Support System 
    PDU         Protocol Data Unit 
    PM          Performance Monitoring 
    PM Function  A MEP capability specified for performance monitoring purposes
       (e.g., Single-Ended Delay, Single-Ended Synthetic Loss) 
    PM Session  A PM Session is the application of a given PM Function between a given
      pair of MEPs and using a given CoS Frame Set over some (possibly
      indefinite) period of time. 
    PM Solution A PM Solution is a set of related requirements that when implemented
       allow a given set of performance metrics to be measured using a
       given set of PM functions. 
    PM Tool     A generic term used to discuss the application of a PM Function.
    Proactive   OAM actions that are carried on continuously to permit timely reporting
       of fault and/or performance status. 
    Resiliency  Performance The number of High Loss Intervals and Consecutive High
       Loss Intervals in T 
    Responder MEP   In a single-ended session, the Responder MEP receives SOAM PDUs,
       from the Controller MEP, and transmits a response to the
       Controller MEP. SOAM-PM 
    RFC         Request for Comment
    Service Frame   An Ethernet frame transmitted across the UNI toward the Service
       Provider or an Ethernet frame transmitted across the UNI toward
       the Subscriber 
    Single-Ended   A type of process where a MEP sends a measurement request and the
       peer MEP replies with the requested information so the originating
       MEP can calculate the measurement.
    Sink MEP    In a dual-ended session, the Sink MEP receives SOAM PDUs, from the
       Controller MEP and performs the performance calculations. 
    SLM         Synthetic Loss Measurement 
    SNMP        Simple Network Management Protocol
    SNMP Agent  An SNMP entity containing one or more command responder and/or
       notification originator applications (along with their associated
       SNMP engine).  Typically implemented in an NE. 
    SNMP Manager   An SNMP entity containing one or more command generator and/or
       notification receiver applications (along with their associated
       SNMP engine). Typically implemented in an EMS or NMS. 
    SOAM        Service OAM 
    SOAM PDU    Service OAM frame, or Protocol Data Unit. Specifically, those PDUs
       defined in [IEEE 802.1ag], [ITU-T Y.1731], or MEF specifications
    Synthetic Traffic   SOAM traffic that emulates service traffic in order to measure
      the performance experience. Delay measurements must use synthetic
      traffic, because user traffic does not contain standardized
      timestamp fields. Other measurements, such as Frame Loss, may also
      use synthetic frames for certain advantages (e.g., ability to
      measure loss in multipoint services). 
    T           Time Interval for SLS Metrics.  The time over which a Performance
       Metric is defined.  T is at least as large as the Measurement
       Interval, and generally consists of multiple Measurement
       Intervals. 
    TC          Textual Conventions 
    TLV         Type Length Value, a method of encoding Objects
    Two-way     A measurement of the performance of frames that flow from the
       Controller MEP to Responder MEP and back again. 
    UML         Unified Modeling Language
    UTC         Coordinated Universal Time 
    UNI         User-to-Network Interface 
    VLAN        Virtual LAN";

  revision "2012-01-13" {
    description     
     "Initial Version.";
  }

  container mefSoamPmMep {

  }

  container mefSoamPmLmObjects {


    /* XXX table comments here XXX */

    list mefSoamLmCfgEntry {

      key "dot1agCfmMdIndex dot1agCfmMaIndex 
           dot1agCfmMepIdentifier mefSoamLmCfgIndex";
      description   
       "The conceptual row of mefSoamLmCfgTable.";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }

      leaf mefSoamLmCfgIndex {
        type uint32 {
          range "1..4294967295";
        }
        description 
         "An index to the Loss Measurement Configuration table which indicates
          the specific measurement session for the MEP.
          
          mefSoamPmMepOperNextIndex needs to be inspected to find an
          available index for row-creation.
          
          Referential integrity is necessary, i.e., the index needs to be
          persistent upon a reboot or restart of a device.  The index
          is never reused for other PM sessions on the same MEP while this
          session is active.  The index value keeps increasing until it
          wraps to 0. This is to facilitate access control based
          on a fixed index for an EMS, since the index is not reused.";
      }

      leaf mefSoamLmCfgType {
        type enumeration {
          enum lmLmm { value 1; }
          enum lmSlm { value 2; }
          enum lmCcm { value 3; }
        }
        config true;
        description 
         "This object specifies what type of Loss Measurement
          will be performed.
          
          lmLmm(1)        LMM SOAM PDU generated and received LMR responses tracked
          lmSlm(2)        SLM SOAM PDU generated and received SLR responses tracked
          lmCcm(3)        CCM SOAM PDU generated and received CCM PDUs tracked
          
          The lmSlm value is required. The lmLmm and lmCcm values are optional.
          
          The lmCcm loss measurement values are only valid for a point-to-point
          MEG. Multipoint MEGs may give unreliable loss measurements.
          
          This object can only be written at row creation time and cannot be 
          modified once it has been created.";
        reference   
         "[Y.1731] [MEF SOAM-PM] R51, R68, O7, R102";
      }

      leaf mefSoamLmCfgVersion {
        type uint32;
        config true;
        description 
         "This object indicates the version of the PDUs used to perform 
          Loss Measurement.
          
          The value is placed in the Version field of the PDU and indicates
          that the PDU format used is the format defined in Y.1731 with
          that version.
          
          The exact PDUs to use are specified by this object in combination with
          mefSoamLmCfgType.
          
          This object can only be written at row creation time and cannot be 
          modified once it has been created.";
        reference   
         "[Y.1731]";
      }

      leaf mefSoamLmCfgEnabled {
        type smiv2:TruthValue;
        config true;
        description 
         "This object specifies whether the Loss Measurement session
          is enabled. 
          
          The value 'true' indicates the Loss Measurement session is enabled and
          SOAM PDUs are sent and/or measurements are collected when the session
          is running according to the scheduling objects (start time, stop time,
          etc.).
          
          The value 'false' indicates the Loss Measurement session is disabled
          and SOAM PDUs are not sent and/or measurements collected.
          
          For a Loss Measurement session to be removed the row is 
          deleted in order to release internal resources.
          
          This object can written/modified after row creation time.
          
          If the LM session is enabled it resumes after shutdown/restart.
          
          If the LM session is disabled the current Measurement Interval is 
          stopped, if it in process at the time, and all the in process calculations
          for the partially completed Measurement Interval are finalized.
          
          This object does not affect whether the single-ended Responder is
          enabled or not, which is enabled or disabled by the 
          mefSoamPmMepLmSingleEndedResponder and 
          mefSoamPmMepSlmSingleEndedResponder objects.";
        reference   
         "[MEF SOAM-PM] R4, R5, R6, O1, R12, R14";
      }

      leaf mefSoamLmCfgMeasurementEnable {
        type bits {
          bit bForwardTransmitedFrames          { position 0; }
          bit bForwardReceivedFrames            { position 1; }
          bit bForwardMinFlr                    { position 2; }
          bit bForwardMaxFlr                    { position 3; }
          bit bForwardAvgFlr                    { position 4; }
          bit bBackwardTransmitedFrames         { position 5; }
          bit bBackwardReceivedFrames           { position 6; }
          bit bBackwardMinFlr                   { position 7; }
          bit bBackwardMaxFlr                   { position 8; }
          bit bBackwardAvgFlr                   { position 9; }
          bit bSoamPdusSent                     { position 10; }
          bit bSoamPdusReceived                 { position 11; }
          bit bAvailForwardHighLoss             { position 12; }
          bit bAvailForwardConsecutiveHighLoss  { position 13; }
          bit bAvailForwardAvailable            { position 14; }
          bit bAvailForwardUnavailable          { position 15; }
          bit bAvailForwardMinFlr               { position 16; }
          bit bAvailForwardMaxFlr               { position 17; }
          bit bAvailForwardAvgFlr               { position 18; }
          bit bAvailBackwardHighLoss            { position 19; }
          bit bAvailBackwardConsecutiveHighLoss { position 20; }
          bit bAvailBackwardAvailable           { position 21; }
          bit bAvailBackwardUnavailable         { position 22; }
          bit bAvailBackwardMinFlr              { position 23; }
          bit bAvailBackwardMaxFlr              { position 24; }
          bit bAvailBackwardAvgFlr              { position 25; }
          bit bMeasuredStatsForwardMeasuredFlr  { position 26; }
          bit bMeasuredStatsBackwardMeasuredFlr { position 27; }
          bit bMeasuredStatsAvailForwardStatus  { position 28; }
          bit bMeasuredStatsAvailBackwardStatus { position 29; }
        }
        config true;
        description 
         "A vector of bits that indicates the type of SOAM LM counters found
          in the mefSoamLmMeasuredStatsTable, mefSoamLmCurrentStatsTable, 
          mefSoamLmHistoryStatsTable, mefSoamLmCurrentAvailStatsTable and
          mefSoamLmHistoryAvailStatsTable that are enabled. 
          
          A bit set to '1' enables the specific SOAM LM counter. A bit set to
          '0' disables the SOAM LM counter.
          
          If a particular SOAM LM counter is not supported the BIT value is
          set to '0'.
          
          Not all SOAM LM counters are supported for all SOAM LM types. 
          
          This object can only be written at row creation time and cannot be 
          modified once it has been created.
          
          bForwardTransmitedFrames (0)
              Enables/disables the mefSoamLmCurrentStatsForwardTransmittedFrames
              and mefSoamLmHistoryStatsForwardTransmittedFrames counters.
          bForwardReceivedFrames(1)
              Enables/disables the mefSoamLmCurrentStatsForwardReceivedFrames
              and mefSoamLmHistoryStatsForwardReceivedFrames counters.
          bForwardMinFlr(2)
              Enables/disables the mefSoamLmCurrentStatsForwardMinFlr
              and mefSoamLmHistoryStatsForwardMinFlr counters.
          bForwardMaxFlr(3)
              Enables/disables the mefSoamLmCurrentStatsForwardMaxFlr
              and mefSoamLmHistoryStatsForwardMaxFlr counters.
          bForwardAvgFlr(4)
              Enables/disables the mefSoamLmCurrentStatsForwardAvgFlr
              and mefSoamLmHistoryStatsForwardAvgFlr counters.
          bBackwardTransmitedFrames(5)
              Enables/disables the mefSoamLmCurrentStatsBackwardTransmittedFrames
              and mefSoamLmHistoryStatsBackwardTransmittedFrames counters.
          bBackwardReceivedFrames(6)
              Enables/disables the mefSoamLmCurrentStatsBackwardReceivedFrames
              and mefSoamLmHistoryStatsBackwardReceivedFrames counters.
          bBackwardMinFlr(7)
              Enables/disables the mefSoamLmCurrentStatsBackwardMinFlr
              and mefSoamLmHistoryStatsBackwardMinFlr counters.
          bBackwardMaxFlr(8)
              Enables/disables the mefSoamLmCurrentStatsBackwardMaxFlr
              and mefSoamLmHistoryStatsBackwardMaxFlr counters.
          bBackwardAvgFlr(9)
              Enables/disables the mefSoamLmCurrentStatsBackwardAvgFlr
              and mefSoamLmHistoryStatsBackwardAvgFlr counters.
          bSoamPdusSent (10)
              Enables/disables the mefSoamLmCurrentStatsSoamPdusSent
              and mefSoamLmHistoryStatsSoamPdusSent counters.
          bSoamPdusReceivedbReceivedMeasurements (11)
              Enables/disables the mefSoamLmCurrentStatsSoamPdusReceived
              and mefSoamLmHistoryStatsSoamPdusReceived counters.
          
          bAvailForwardHighLoss(12)
              Enables/disables the mefSoamLmCurrentAvailStatsForwardHighLoss
              and mefSoamLmHistoryAvailStatsForwardHighLoss counters.
          bAvailForwardConsecutiveHighLoss(13)
              Enables/disables the mefSoamLmCurrentAvailStatsForwardConsecutiveHighLoss
              and mefSoamLmHistoryAvailStatsForwardConsecutiveHighLoss counters.
          bAvailForwardAvailable(14)
              Enables/disables the mefSoamLmCurrentAvailStatsForwardAvailable
              and mefSoamLmHistoryAvailStatsForwardAvailable counters.
          bAvailForwardUnavailable(15)
              Enables/disables the mefSoamLmCurrentAvailStatsForwardUnavailable
              and mefSoamLmHistoryAvailStatsForwardUnavailable counters.
          bAvailForwardMinFlr(16)
              Enables/disables the mefSoamLmCurrentAvailStatsForwardMinFlr
              and mefSoamLmHistoryAvailStatsForwardMinFlr counters.
          bAvailForwardMaxFlr(17)
              Enables/disables the mefSoamLmCurrentAvailStatsForwardMaxFlr
              and mefSoamLmHistoryAvailStatsForwardMaxFlr counters.
          bAvailForwardAvgFlr(18)
              Enables/disables the mefSoamLmCurrentAvailStatsForwardAvgFlr
              and mefSoamLmHistoryAvailStatsForwardAvgFlr counters.
          
          bAvailBackwardHighLoss(19)
              Enables/disables the mefSoamLmCurrentAvailStatsBackwardHighLoss
              and mefSoamLmHistoryAvailStatsBackwardHighLoss counters.
          bAvailBackwardConsecutiveHighLoss(20)
              Enables/disables the mefSoamLmCurrentAvailStatsBackwardConsecutiveHighLoss
              and mefSoamLmHistoryAvailStatsBackwardConsecutiveHighLoss counters.
          bAvailBackwardAvailable(21)
              Enables/disables the mefSoamLmCurrentAvailStatsBackwardAvailable
              and mefSoamLmHistoryAvailStatsBackwardAvailable counters.
          bAvailBackwardUnavailable(22)
              Enables/disables the mefSoamLmCurrentAvailStatsBackwardUnavailable
              and mefSoamLmHistoryAvailStatsBackwardUnavailable counters.
          bAvailBackwardMinFlr(23)
              Enables/disables the mefSoamLmCurrentAvailStatsBackwardMinFlr
              and mefSoamLmHistoryAvailStatsBackwardMinFlr counters.
          bAvailBackwardMaxFlr(24)
              Enables/disables the mefSoamLmCurrentAvailStatsBackwardMaxFlr
              and mefSoamLmHistoryAvailStatsBackwardMaxFlr counters.
          bAvailBackwardAvgFlr(25)
              Enables/disables the mefSoamLmCurrentAvailStatsBackwardAvgFlr
              and mefSoamLmHistoryAvailStatsBackwardAvgFlr counters.
          
          bMeasuredStatsForwardMeasuredFlr(26)
              Enables/disables the mefSoamLmMeasuredStatsForwardFlr counter.
          bMeasuredStatsBackwardMeasuredFlr(27)
              Enables/disables the mefSoamLmMeasuredStatsBackwardFlr counter.
          bMeasuredStatsAvailForwardStatus(28)
              Enables/disables the mefSoamLmMeasuredStatsAvailForwardStatus counter.
          bMeasuredStatsAvailBackwardStatus(29)
              Enables/disables the mefSoamLmMeasuredStatsAvailBackwardStatus counter.";
        reference   
         "[Y.1731]";
      }

      leaf mefSoamLmCfgMessagePeriod {
        type mef-soam:MefSoamTcMeasurementPeriodType;
        units "ms";
        config true;
        description 
         "This object specifies the interval between Loss Measurement
          OAM message transmission. For Loss Measurement monitoring 
          applications the default value is 1 sec. 
          
          This object is not applicable if mefSoamLmCfgType is set to lmCcm
          and is ignored for that Loss Measurement Type.
          
          This object can only be written at row creation time and cannot be 
          modified once it has been created.";
        reference   
         "[MEF SOAM-PM] R76, R77, D29, D30";
      }

      leaf mefSoamLmCfgPriority {
        type ieee8021-tc:IEEE8021PriorityValue;
        config true;
        description 
         "This object specifies the Loss Measurement OAM message priority
          as well as the priority of the service/OAM traffic to be monitored.
          Only frames of the same Class of Service are counted.        
          
          The default value is to be the value which yields the lowest frame 
          loss.
          
          This object is not applicable if mefSoamLmCfgType is set to lmCcm.
          
          This object can only be written at row creation time and cannot be 
          modified once it has been created.";
        reference   
         "[MEF SOAM-PM] R1, R2, R71, D28, R72, R73, R105-R109, D45; 
          [MEF 10.2.1] Section 6.8";
      }

      leaf mefSoamLmCfgFrameSize {
        type uint32 {
          range "64..9600";
        }
        units "bytes";
        config true;
        description 
         "This object specifies the Loss Measurement frame size between
          64 bytes and the maximum transmission unit of the EVC. 
          
          The range of frame sizes from 64 through 2000 octets need to be
          supported, and the range of frame sizes from 2001 through 9600 octets
          is suggested be supported.  
          
          The adjustment to the frame size of the standard frame size is 
          accomplished by the addition of a Data or Test TLV. A Data or Test TLV
          is only added to the frame if the frame size is greater than 64 bytes.
          
          This object is only valid for the entity transmitting the Loss
          Measurement frames, type 'lmSlm', and is ignored by the
          entity receiving frames. It is not applicable for the 'lmCcm' or 
          'lmLmm' types.
          
          This object can only be written at row creation time and cannot be 
          modified once it has been created.";
        reference   
         "[MEF SOAM-PM] R78, R79, D31, D32 [Y.1731]";
      }

      leaf mefSoamLmCfgDataPattern {
        type mef-soam:MefSoamTcDataPatternType;
        config true;
        description 
         "This object specifies the LM data pattern included in a Data TLV
          when the size of the LM frame is determined by the 
          mefSoamLmFrameSize object and mefSoamLmTestTlvIncluded is 'false'.
          
          If the frame size object does not define the LM frame size or 
          mefSoamLmTestTlvIncluded is 'true' the value of this object is 
          ignored.
          
          This object can only be written at row creation time and cannot be 
          modified once it has been created.";
      }

      leaf mefSoamLmCfgTestTlvIncluded {
        type smiv2:TruthValue;
        config true;
        description 
         "Indicates whether a Test TLV or Data TLV is included when the size
          of the LM frame is determined by the mefSoamLmFrameSize object.
          
          A value of 'true' indicates that the Test TLV is to be included. A 
          value of 'false' indicates that the Data TLV is to be included.
          
          If the frame size object does not define the LM frame size
          the value of this object is ignored.
          
          This object can only be written at row creation time and cannot be 
          modified once it has been created.";
        reference   
         "[Y.1731] 9.3";
      }

      leaf mefSoamLmCfgTestTlvPattern {
        type mef-soam:MefSoamTcTestPatternType;
        config true;
        description 
         "This object specifies the type of test pattern to be
          sent in the LM frame Test TLV when the size of LM PDU is 
          determined by the mefSoamLmFrameSize object and 
          mefSoamLmTestTlvIncluded is 'true'. If the frame size object
          does not define the LM frame size or mefSoamLmTestTlvIncluded
          is 'false' the value of this object is ignored.
          
          This object can only be written at row creation time and cannot be 
          modified once it has been created.";
      }

      leaf mefSoamLmCfgMeasurementInterval {
        type uint32 {
          range "1..525600";
        }
        units "minutes";
        config true;
        description 
         "This object specifies the Measurement Interval for FLR statistics, in minutes.
          
          A Measurement Interval of 15 minutes needs to be supported, other intervals
          may be supported.
          
          This object can only be written at row creation time and cannot be 
          modified once it has been created.";
        reference   
         "[MEF SOAM-PM] R16, R17, R110, R111, D46";
      }

      leaf mefSoamLmCfgNumIntervalsStored {
        type uint32 {
          range "2..1000";
        }
        config true;
        description 
         "This object specifies the number of completed Measurement Intervals
          to store in the history statistic table (mefSoamLmHistoryStatsTable)
          and the history availability statistic table
          (mefSoamLmHistoryAvailStatsTable).
          
          At least 32 completed Measurement Intervals need to be stored. 96 
          Measurement Intervals are recommended to be stored.
          
          This object can only be written at row creation time and cannot be 
          modified once it has been created.";
        reference   
         "[MEF SOAM-PM] R21, D8, D9";
      }

      leaf mefSoamLmCfgDestMacAddress {
        type yang:mac-address;
        config true;
        description 
         "The Target or Destination MAC Address Field to be transmitted. 
          
          If mefSoamLmCfgType is 'lmCcm', the destination MAC address is always a 
          multicast address indicating the level of the MEG: 01-80-c2-00-00-3y,
          where y is the level of the MEG. An error is returned if this object
          is set to any other value.
          
          If mefSoamLmCfgType is 'lmLmm' or 'lmSlm', the destination address is
          the unicast address of the destination MEP. An error is returned if 
          this object is set to a multicast address.
          
          This address will be used if the value of the object
          mefSoamLmDestIsMepId is 'false'. 
          
          This object is only valid for the entity transmitting the 
          SOAM LM frames and is ignored by the entity receiving 
          SOAM LM frames.
          
          This object can only be written at row creation time and cannot be 
          modified once it has been created.";
        reference   
         "[MEF SOAM-PM] R70, R104";
      }

      leaf mefSoamLmCfgDestMepId {
        type ieee8021-cfm:Dot1agCfmMepIdOrZero;
        config true;
        description 
         "The Maintenance Association End Point Identifier of
          another MEP in the same Maintenance Association to which
          the SOAM LM frame is to be sent.
          
          This address will be used if the value of the column
          mefSoamLmDestIsMepId is 'true'. A value of zero
          means that the destination MEP ID has not been configured.
          
          This object is only valid for the entity transmitting the Loss
          Measurement frames, types 'lmLmm' and 'lmSlm'. It is not applicable for
          the 'lmCcm' type.
          
          This object can only be written at row creation time and cannot be 
          modified once it has been created.";
        reference   
         "[MEF SOAM-PM] R70, R104";
      }

      leaf mefSoamLmCfgDestIsMepId {
        type smiv2:TruthValue;
        config true;
        description 
         "A value of 'true' indicates that MEPID of the target MEP is used for
          SOAM LM frame transmission.
          
          A value of 'false' indicates that the MAC address of the
          target MEP is used for SOAM LM frame transmission.
          
          This object is only valid for the entity transmitting the Loss
          Measurement frames, types 'lmLmm' and 'lmSlm'. It is not applicable for
          the 'lmCcm' type.
          
          This object can only be written at row creation time and cannot be 
          modified once it has been created.";
        reference   
         "[MEF SOAM-PM] R70, R104";
      }

      leaf mefSoamLmCfgStartTimeType {
        type mef-soam:MefSoamTcOperationTimeType;
        config true;
        description 
         "This object specifies the type of start time of the SOAM LM
          session. The start time can be disabled (none), immediate, relative,
          or fixed.
          
          The value of 'none' is illegal and a write error will be returned
          if this value is used.
          
          The value of 'immediate' starts the SOAM LM session when the 
          mefSoamLmCfgEnabled is true.
          
          The value of 'fixed' starts the SOAM LM session when the 
          mefSoamLmFixedStartDateAndTime is less than or equal to the current
          system date and time and mefSoamLmCfgEnabled is true. This value is used
          to implement an On-Demand fixed time PM session.
          
          The value of 'relative' starts the SOAM LM session when the current
          system date and time minus the mefSoamLmRelativeStartTime is greater
          than or equal to the system date and time when the mefSoamLmStartTimeType
          object was written and mefSoamLmCfgEnabled is true. This value is used
          to implement an On-Demand relative time PM session.
          
          This object can only be written at row creation time and cannot be 
          modified once it has been created.";
        reference   
         "[MEF SOAM-PM] R3, R7, R8, D1";
      }

      leaf mefSoamLmCfgFixedStartDateAndTime {
        type smiv2:DateAndTime;
        config true;
        description 
         "This object specifies the fixed start date/time for the 
          SOAM Loss Measurement session. This object is used only used if 
          mefSoamLmStartTimeType is 'fixed' and is ignored otherwise.
          
          The default value is year 0000, month 01, day 01, time 00:00:00.00.
          
          This object can only be written at row creation time and cannot be 
          modified once it has been created.";
        reference   
         "[MEF SOAM-PM] R9";
      }

      leaf mefSoamLmCfgRelativeStartTime {
        type smiv2:TimeInterval;
        config true;
        description 
         "This object specifies the relative start time, from the
          current system time, for the SOAM LM session.  This
          object is used only if mefSoamLmStartTimeType is 'relative' and is 
          ignored otherwise.
          
          This object can only be written at row creation time and cannot be 
          modified once it has been created.";
        reference   
         "[MEF SOAM-PM] R9";
      }

      leaf mefSoamLmCfgStopTimeType {
        type mef-soam:MefSoamTcOperationTimeType;
        config true;
        description 
         "This object specifies the type of stop time to terminate the
          SOAM LM session. The stop time can be forever (none), relative, or 
          fixed.
          
          The value of 'none' indicates that the SOAM LM session never ends once it
          has started unless it the session is disabled.
          
          The value of 'immediate' is illegal and a write error will be returned
          if this value is used.
          
          The value of 'fixed' stops the SOAM LM session when the 
          mefSoamLmFixedStopDateAndTime is less than or equal
          to the current system date and time. This
          value is used to implement an On-Demand fixed time PM session.
          
          The value of 'relative' stops the SOAM LM session when the time 
          indicated by mefSoamLmRelativeStopTime has passed since the session
          start time as determined by the mefSoamLmCfgStartTimeType, 
          mefSoamLmCfgFixedStartDateAndTime and mefSoamLmCfgRelativeStartTime
          objects. This value is used to implement an On-Demand relative time 
          PM session.
          
          This object can only be written at row creation time and cannot be 
          modified once it has been created.";
        reference   
         "[MEF SOAM-PM] R3, R10, D2";
      }

      leaf mefSoamLmCfgFixedStopDateAndTime {
        type smiv2:DateAndTime;
        config true;
        description 
         "This object specifies the fixed stop date/time for the 
          SOAM Loss Measurement session. This object is used only used 
          if mefSoamLmStopTimeType is 'fixed' and is ignored otherwise.
          
          The default value is year 0000, month 01, day 01, time 00:00:00.00.
          
          This object can only be written at row creation time and cannot be 
          modified once it has been created.";
        reference   
         "[MEF SOAM-PM] R10, R13";
      }

      leaf mefSoamLmCfgRelativeStopTime {
        type smiv2:TimeInterval;
        config true;
        description 
         "This object specifies the relative stop time, from the
          session start time, to stop the SOAM LM session.  This
          object is used only if mefSoamLmStopTimeType is 'relative' and is 
          ignored otherwise.
          
          This object can only be written at row creation time and cannot be 
          modified once it has been created.";
        reference   
         "[MEF SOAM-PM] R11";
      }

      leaf mefSoamLmCfgRepetitionTime {
        type uint32 {
          range "0..31536000";
        }
        units "seconds";
        config true;
        description 
         "This object specifies a configurable repetition time between
          Measurement Intervals in a Loss Measurement session, in seconds.
          
          If the value is 0 (none), there is no time gap between the end of one
          Measurement Interval and the start of a new Measurement Interval.
          This is the normal usage case.
          
          If the value is greater than 0 but less than or equal to the measurement
          interval, an error is returned.
          
          If the value is greater than one Measurement Interval there is time gap
          between the end of one Measurement Interval and the start of the next
          Measurement Interval.  The repetition time specifies the time between
          the start of consecutive Measurement Intervals; hence the gap between
          the end of one Measurement Interval and the start of the next is equal
          to the difference between the repetition time and the measurement
          interval.  During this gap, no SOAM PDUs are sent for this session and
          no measurements are made.
          
          This object can only be written at row creation time and cannot be 
          modified once it has been created.";
        reference   
         "[MEF SOAM-PM] R18, D3, R19, R20";
      }

      leaf mefSoamLmCfgAlignMeasurementIntervals {
        type smiv2:TruthValue;
        config true;
        description 
         "This object specifies whether the Measurement Intervals for
          the Loss Measurement session are aligned with a zero offset to
          real time.
          
          The value 'true' indicates that each Measurement Interval starts
          at a time which is aligned to NE time source hour, if the repetition
          time (or the Measurement Interval, if the repetition time is 0) is
          a factor of an hour, i.e. 60min/15min = 4. For instance, a
          Measurement Interval/repetition time of 15 minutes would stop/start 
          the Measurement Interval at 0, 15, 30, and 45 minutes of an hour. A 
          Measurement Interval/Repetition Time of 7 minutes would not align
          to the hour since 7 minutes is NOT a factor of an hour, i.e.
          60min/7min = 8.6.  In this case the behavior is the same as if the
          object is set to 'false'.
          
          The value 'false' indicates that the first Measurement Interval starts
          at an arbitrary time and each subsequent Measurement Interval starts
          at a time which is determined by mefSoamLmCfgRepetitionTime.
          
          This object can only be written at row creation time and cannot be 
          modified once it has been created.";
        reference   
         "[MEF SOAM-PM] D4, D5, D6";
      }

      leaf mefSoamLmCfgAlignMeasurementOffset {
        type uint32 {
          range "0..525600";
        }
        units "minutes";
        config true;
        description 
         "This object specifies the offset in minutes from the time of day value 
          if mefSoamLmCfgAlignMeasurementIntervals is 'true' and the repetition 
          time is a factor of 60 minutes. If not, the value of this object
          is ignored.
          
          If the Measurement Interval is 15 minutes and 
          mefSoamLmCfgAlignMeasurementIntervals is true and if this object was
          set to 5 minutes, the Measurement Intervals would start at 5, 20, 35, 50
          minutes past each hour.
          
          This object can only be written at row creation time and cannot be 
          modified once it has been created.";
        reference   
         "[MEF SOAM-PM] D7";
      }

      leaf mefSoamLmCfgAvailabilityMeasurementInterval {
        type uint32 {
          range "1..525600";
        }
        units "minutes";
        config true;
        description 
         "This object specifies the availability Measurement Interval in 
          minutes.
          
          A Measurement Interval of 15 minutes is to be supported, other intervals
          can be supported.
          
          This object can only be written at row creation time and cannot be 
          modified once it has been created.";
        reference   
         "[MEF SOAM-PM] R16, R17";
      }

      leaf mefSoamLmCfgAvailabilityNumConsecutiveMeasPdus {
        type uint32 {
          range "1..1000000";
        }
        config true;
        description 
         "This object specifies a configurable number of consecutive
          loss measurement PDUs to be used in evaluating the 
          availability/unavailability status of each availability
          indicator per MEF 10.2.1.  Loss Measurement PDUs (LMMs, CCMs or
          SLMs) are sent regularly with a period defined by
          mefSoamLmCfgMessagePeriod.  Therefore, this object, when 
          multiplied by mefSoamLmCfgMessagePeriod, is equivalent to
          the Availability parameter of 'delta_t' as specified by MEF 10.2.1.
          
          If the mefSoamLmCfgType is lmLMM or lmCCM, this object defines the
          number of LMM or CCM PDUs transmitted during each 'delta_t' period.
          The Availability flr for a given 'delta_t' can be calculated based
          on the counters in the last LMM/R or CCM during this 'delta_t' and
          the last LMM/R or CCM in the previous 'delta_t'.
          
          If the mefSoamLmCfgType is lmSLM, this object defines the number
          of SLM PDUs transmitted during each 'delta_t' period.  The
          Availability flr for a given 'delta_t' is calculated based on the
          number of those SLM PDUs that are lost.
          
          If the mefSoamLmCfgType is lmLMM or lmCCM, the number range of 1
          through 10 must be supported. The number range of 10 through 1000000
          may be supported, but is not mandatory.
          
          If the mefSoamLmCfgType is lmSLM, the number range of 10 through
          100 must be supported. The number range of 100 through 1000000
          may be supported, but is not mandatory.
          
          This object can only be written at row creation time and cannot be 
          modified once it has been created.";
        reference   
         "[MEF 10.2.1] Section 7.9.8; [MEF SOAM-PM] R80, D33, R81";
      }

      leaf mefSoamLmCfgAvailabilityFlrThreshold {
        type uint32 {
          range "0..100000";
        }
        units "milli-percent";
        config true;
        description 
         "This object specifies a configurable availability threshold to be
          used in evaluating the availability/unavailability status of an
          availability indicator per MEF 10.2.1. The availability threshold range
          of 0.00 (0) through 1.00 (100000) is supported. This parameter is 
          equivalent to the Availability parameter of 'C' as specified by 
          MEF 10.2.1.
          
          Units are in milli-percent, where 1 indicates 0.001 percent.
          
          This object can only be written at row creation time and cannot be 
          modified once it has been created.";
        reference   
         "[MEF 10.2.1] Section 7.9.8; [MEF SOAM-PM] R81, R82, D34";
      }

      leaf mefSoamLmCfgAvailabilityNumConsecutiveIntervals {
        type uint32 {
          range "1..1000";
        }
        config true;
        description 
         "This object specifies a configurable number of consecutive
          availability indicators to be used to determine a change in the
          availability status as indicated by MEF 10.2.1. This parameter is 
          equivalent to the Availability parameter of 'n' as specified
          by MEF 10.2.1.
          
          The number range of 1 through 10 must be supported. The number range
          of 1 through 1000 may be supported, but is not mandatory.
          
          This object can only be written at row creation time and cannot be 
          modified once it has been created.";
        reference   
         "[MEF 10.2.1] Section 7.9.8; [MEF SOAM-PM] R80, D33";
      }

      leaf mefSoamLmCfgAvailabilityNumConsecutiveHighFlr {
        type uint32 {
          range "1..1000";
        }
        config true;
        description 
         "This object specifies a configurable number of consecutive
          availability indicators to be used for assessing CHLI.  This
          parameter is equivalent to the Resilency parameter of 'p' as
          specified by MEF 10.2.1.
          
          mefSoamLmCfgAvailabilityNumConsecutiveHighFlr must be strictly less than 
          mefSoamLmCfgAvailabilityNumConsecutiveIntervals. If not, the count of high
          loss intervals over time, mefSoamLmAvailabilityHighLoss, and the count 
          of consecutive high loss levels, mefSoamLmAvailabilityConsecutiveHighLoss,
          is disabled.
          
          The number range of 1 through 10 must be supported. The number range
          of 1 through 1000 may be supported, but is not mandatory.
          
          This object can only be written at row creation time and cannot be 
          modified once it has been created.";
        reference   
         "[MEF 10.2.1] Section 7.9.8; [MEF SOAM-PM] R86, D35, D36";
      }

      leaf mefSoamLmCfgSessionType {
        type mef-soam:MefSoamTcSessionType;
        config true;
        description 
         "This object indicates whether the current session is defined to
          be 'Proactive' or 'On-Demand'. A value of 'proactive'
          indicates the current session is 'Proactive'. A value of 'onDemand'
          indicates the current session is 'On-Demand'.
          
          This object can only be written at row creation time and cannot be 
          modified once it has been created.";
        reference   
         "[MEF SOAM-PM] R3";
      }

      leaf mefSoamLmCfgSessionStatus {
        type mef-soam:MefSoamTcStatusType;
        description 
         "This object indicates the current status of the LM session. A value
          of 'active' indicates the current LM session is active, i.e. the current
          time lies between the start time and the stop time, and
          mefSoamLmCfgEnabled is true. A value of 'notActive' indicates the
          current LM session is not active, i.e. it has not started yet, has
          stopped upon reaching the stop time, or is disabled.";
      }

      leaf mefSoamLmCfgHistoryClear {
        type smiv2:TruthValue;
        config true;
        description 
         "This object when written clears the Loss Measurement history
          Table (mefSoamLmHistoryStatsTable) - all rows are deleted.
          When read the value always returns 'false'. 
          
          Writing this value does not change the current stat table,
          nor any of the items in the configuration table.
          Writing this value during row creation has no effect.";
      }

      leaf mefSoamLmCfgRowStatus {
        type smiv2:RowStatus;
        config true;
        description 
         "The status of the row.
          
          The writable columns in a row cannot be changed if the row
          is active, except for mefSoamLmCfgHistoryClear and mefSoamLmCfgEnabled
          objects. All columns must have a valid value before a row 
          can be activated.  ";
      }
    }


    /* XXX table comments here XXX */

    list mefSoamLmMeasuredStatsEntry {

      key "dot1agCfmMdIndex dot1agCfmMaIndex 
           dot1agCfmMepIdentifier mefSoamLmCfgIndex";
      description   
       "The conceptual row of mefSoamLmMeasuredStatsTable";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        config true;
        description 
         "Automagically generated leafref leaf.";
      }

      leaf mefSoamLmMeasuredStatsForwardFlr {
        type uint32 {
          range "0..100000";
        }
        units "milli-percent";
        description 
         "This object contains the last frame loss ratio in the forward direction
          calculated by this MEP. The FLR value
          is a ratio that is expressed as a percent with a value of 0 (ratio 
          0.00) through 100000 (ratio 1.00).
          
          Units are in milli-percent, where 1 indicates 0.001 percent.";
        reference   
         "[MEF SOAM-PM] D37";
      }

      leaf mefSoamLmMeasuredStatsBackwardFlr {
        type uint32 {
          range "0..100000";
        }
        units "milli-percent";
        description 
         "This object contains the last frame loss ratio in the backward direction
          calculated by this MEP. The FLR value
          is a ratio that is expressed as a percent with a value of 0 (ratio 
          0.00) through 100000 (ratio 1.00).
          
          Units are in milli-percent, where 1 indicates 0.001 percent.";
        reference   
         "[MEF SOAM-PM] D37";
      }

      leaf mefSoamLmMeasuredStatsAvailForwardStatus {
        type mef-soam:MefSoamTcAvailabilityType;
        description 
         "This object indicates the availability status (the outcome of the
          last known availability indicator) in the forward direction.
          Note that the status of an availability indicator is not known until
          the loss for a number of subsequent availability indicators has been
          calculated (as determined by 
          mefSoamLmCfgAvailabilityNumConsecutiveIntervals)";
        reference   
         "[MEF SOAM-PM] R83";
      }

      leaf mefSoamLmMeasuredStatsAvailBackwardStatus {
        type mef-soam:MefSoamTcAvailabilityType;
        description 
         "This object indicates the availability status (the outcome of the
          last availability indicator) in the backward direction.
          Note that the status of an availability indicator is not known until
          the loss for a number of subsequent availability indicators has been
          calculated (as determined by 
          mefSoamLmCfgAvailabilityNumConsecutiveIntervals)";
        reference   
         "[MEF SOAM-PM] R83";
      }

      leaf mefSoamLmMeasuredStatsAvailForwardLastTransitionTime {
        type smiv2:DateAndTime;
        description 
         "This object indicates the time of the last transition
          between available and unavailable in the forward direction.
          
          If there have been no transitions since the Loss Measurement
          Session was started, this is set to 0.";
        reference   
         "[MEF SOAM-PM] R83";
      }

      leaf mefSoamLmMeasuredStatsAvailBackwardLastTransitionTime {
        type smiv2:DateAndTime;
        description 
         "This object indicates the time of the last transition
          between available and unavailable in the backward direction.
          
          If there have been no transitions since the Loss Measurement
          Session was started, this is set to 0.";
        reference   
         "[MEF SOAM-PM] R83";
      }
    }


    /* XXX table comments here XXX */

    list mefSoamLmCurrentAvailStatsEntry {

      key "dot1agCfmMdIndex dot1agCfmMaIndex 
           dot1agCfmMepIdentifier mefSoamLmCfgIndex";
      description   
       "The conceptual row of mefSoamLmCurrentAvailStatsTable";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        config true;
        description 
         "Automagically generated leafref leaf.";
      }

      leaf mefSoamLmCurrentAvailStatsIndex {
        type uint32;
        description 
         "The index for the current availability Measurement Interval for this
          PM session.  This value will become the value for
          mefSoamLmHistoryAvailStatsIndex once the Measurement Interval
          is completed.  The duration of the Measurement Interval is specified
          by mefSoamLmCfgAvailabilityMeasurementInterval.
          
          Measurement Interval indexes are assigned sequentially by
          the SNMP Agent.  The first Measurement Interval that occurs after
          the session is started is assigned index 1.";
      }

      leaf mefSoamLmCurrentAvailStatsStartTime {
        type smiv2:DateAndTime;
        description 
         "The time that the current Measurement Interval started.";
        reference   
         "[MEF SOAM-PM] R87, R112";
      }

      leaf mefSoamLmCurrentAvailStatsElapsedTime {
        type smiv2:TimeInterval;
        description 
         "The time that the current Measurement Interval has been running, in 0.01
          seconds.";
        reference   
         "[MEF SOAM-PM] R24, R87, R112";
      }

      leaf mefSoamLmCurrentAvailStatsSuspect {
        type smiv2:TruthValue;
        description 
         "Whether the Measurement Interval has been marked as suspect.
          
          The object is set to false at the start of a measurement
          interval. It is set to true when there is a discontinuity in the 
          performance measurements during the Measurement Interval.  Conditions
          for a discontinuity include, but are not limited to the following:
          
          1 - The local time-of-day clock is adjusted by at least 10 seconds
          2 - The conducting of a performance measurement is halted before the
              current Measurement Interval is completed
          3 - A local test, failure, or reconfiguration that disrupts service";
        reference   
         "[MEF SOAM-PM] R39, R40, R41";
      }

      leaf mefSoamLmCurrentAvailStatsForwardHighLoss {
        type uint32;
        description 
         "This object is the number of high loss intervals (HLI) over
          time in the forward direction. 
          
          The value starts at 0 and increments for every HLI that occurs.
          This parameter is equivalent to 'L Sub T' found in MEF 10.2.1.";
        reference   
         "[MEF 10.2.1] 6.9.9; [MEF SOAM-PM] R87";
      }

      leaf mefSoamLmCurrentAvailStatsBackwardHighLoss {
        type uint32;
        description 
         "This object is the number of high loss intervals (HLI) over
          time in the backwards direction. 
          
          The value starts at 0 and increments for every HLI that occurs.
          This parameter is equivalent to 'L Sub T' found in MEF 10.2.1.";
        reference   
         "[MEF 10.2.1] 6.9.9; [MEF SOAM-PM] R87";
      }

      leaf mefSoamLmCurrentAvailStatsForwardConsecutiveHighLoss {
        type uint32;
        description 
         "This object is the number of consecutive high loss intervals
          (CHLI) over time in the forward direction. 
          
          The value starts at 0 and increments for every HLI that occurs
          that is determined to fall within a CHLI.
          This parameter is equivalent to 'B Sub T' found in MEF 10.2.1.";
        reference   
         "[MEF 10.2.1] 6.9.9; [MEF SOAM-PM] R87";
      }

      leaf mefSoamLmCurrentAvailStatsBackwardConsecutiveHighLoss {
        type uint32;
        description 
         "This object is the number of consecutive high loss intervals
          (CHLI) over time in the backward direction. 
          
          The value starts at 0 and increments for every HLI that occurs
          that is determined to fall within a CHLI.
          This parameter is equivalent to 'B Sub T' found in MEF 10.2.1.";
        reference   
         "[MEF 10.2.1] 6.9.9; [MEF SOAM-PM] R87";
      }

      leaf mefSoamLmCurrentAvailStatsForwardAvailable {
        type yang:gauge32;
        description 
         "This object contains the number of availability indicators 
          evaluated as available in the forward direction by this MEP during
          this Measurement Interval.";
        reference   
         "[MEF SOAM-PM] R87; [MEF 10.2.1]";
      }

      leaf mefSoamLmCurrentAvailStatsBackwardAvailable {
        type yang:gauge32;
        description 
         "This object contains the number of availability indicators 
          evaluated as available in the backward direction by this MEP during
          this Measurement Interval.";
        reference   
         "[MEF SOAM-PM] R87";
      }

      leaf mefSoamLmCurrentAvailStatsForwardUnavailable {
        type yang:gauge32;
        description 
         "This object contains the number of availability indicators 
          evaluated as unavailable in the forward direction by this MEP during
          this Measurement Interval.";
        reference   
         "[MEF SOAM-PM] R87";
      }

      leaf mefSoamLmCurrentAvailStatsBackwardUnavailable {
        type yang:gauge32;
        description 
         "This object contains the number of availability indicators 
          evaluated as unavailable in the backward direction by this MEP
          during this Measurement Interval.";
        reference   
         "[MEF SOAM-PM] R87";
      }

      leaf mefSoamLmCurrentAvailStatsForwardMinFlr {
        type uint32 {
          range "0..100000";
        }
        units "milli-percent";
        description 
         "This object contains the minimum one-way availability flr in the forward
          direction, from among the set of availability flr values calculated by
          the MEP in this Measurement Interval.  There is one availability flr 
          value for each 'delta_t' time period within the Measurement Interval, as
          specified in MEF 10.2.1.
          
          The flr value is a ratio that is expressed as a 
          percent with a value of 0 (ratio 0.00) through 100000 (ratio 1.00).
          
          Units are in milli-percent, where 1 indicates 0.001 percent.";
        reference   
         "[MEF SOAM-PM] D37";
      }

      leaf mefSoamLmCurrentAvailStatsForwardMaxFlr {
        type uint32 {
          range "0..100000";
        }
        units "milli-percent";
        description 
         "This object contains the maximum one-way availability flr in the forward
          direction, from among the set of availability flr values calculated by
          the MEP in this Measurement Interval.  There is one availability flr 
          value for each 'delta_t' time period within the Measurement Interval, as
          specified in MEF 10.2.1.
          
          The flr value is a ratio that is expressed as a 
          percent with a value of 0 (ratio 0.00) through 100000 (ratio 1.00).
          
          Units are in milli-percent, where 1 indicates 0.001 percent.";
        reference   
         "[MEF SOAM-PM] D37";
      }

      leaf mefSoamLmCurrentAvailStatsForwardAvgFlr {
        type uint32 {
          range "0..100000";
        }
        units "milli-percent";
        description 
         "This object contains the average one-way availability flr in the forward
          direction, from among the set of availability flr values calculated by
          the MEP in this Measurement Interval.  There is one availability flr 
          value for each 'delta_t' time period within the Measurement Interval, as
          specified in MEF 10.2.1.
          
          The flr value is a ratio that is expressed as a 
          percent with a value of 0 (ratio 0.00) through 100000 (ratio 1.00).
          
          Units are in milli-percent, where 1 indicates 0.001 percent.";
        reference   
         "[MEF SOAM-PM] D37";
      }

      leaf mefSoamLmCurrentAvailStatsBackwardMinFlr {
        type uint32 {
          range "0..100000";
        }
        units "milli-percent";
        description 
         "This object contains the minimum one-way availability flr in the backward
          direction, from among the set of availability flr values calculated by
          the MEP in this Measurement Interval.  There is one availability flr 
          value for each 'delta_t' time period within the Measurement Interval, as
          specified in MEF 10.2.1.
          
          The flr value is a ratio that is expressed as a 
          percent with a value of 0 (ratio 0.00) through 100000 (ratio 1.00).
          
          Units are in milli-percent, where 1 indicates 0.001 percent.";
        reference   
         "[MEF SOAM-PM] D37";
      }

      leaf mefSoamLmCurrentAvailStatsBackwardMaxFlr {
        type uint32 {
          range "0..100000";
        }
        units "milli-percent";
        description 
         "This object contains the maximum one-way availability flr in the backward
          direction, from among the set of availability flr values calculated by
          the MEP in this Measurement Interval.  There is one availability flr 
          value for each 'delta_t' time period within the Measurement Interval, as
          specified in MEF 10.2.1.
          
          The flr value is a ratio that is expressed 
          as a percent with a value of 0 (ratio 0.00) through 100000 (ratio 1.00).
          
          Units are in milli-percent, where 1 indicates 0.001 percent.";
        reference   
         "[MEF SOAM-PM] D37";
      }

      leaf mefSoamLmCurrentAvailStatsBackwardAvgFlr {
        type uint32 {
          range "0..100000";
        }
        units "milli-percent";
        description 
         "This object contains the average one-way availability flr in the backward
          direction, from among the set of availability flr values calculated by
          the MEP in this Measurement Interval.  There is one availability flr 
          value for each 'delta_t' time period within the Measurement Interval, as
          specified in MEF 10.2.1.
          
          The flr value is a ratio that is expressed as a 
          percent with a value of 0 (ratio 0.00) through 100000 (ratio 1.00).
          
          Units are in milli-percent, where 1 indicates 0.001 percent.";
        reference   
         "[MEF SOAM-PM] D37";
      }
    }


    /* XXX table comments here XXX */

    list mefSoamLmCurrentStatsEntry {

      key "dot1agCfmMdIndex dot1agCfmMaIndex 
           dot1agCfmMepIdentifier mefSoamLmCfgIndex";
      description   
       "The conceptual row of mefSoamLmCurrentStatsTable";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        config true;
        description 
         "Automagically generated leafref leaf.";
      }

      leaf mefSoamLmCurrentStatsIndex {
        type uint32;
        description 
         "The index for the current Measurement Interval for this
          PM session.  This value will become the value for
          mefSoamLmHistoryStatsIndex once the Measurement Interval
          is completed.
          
          Measurement Interval indexes are assigned sequentially by
          the SNMP Agent.  The first Measurement Interval that occurs after
          the session is started is assigned index 1.";
      }

      leaf mefSoamLmCurrentStatsStartTime {
        type smiv2:DateAndTime;
        description 
         "The time that the current Measurement Interval started.";
        reference   
         "[MEF SOAM-PM] R22, R87, R112";
      }

      leaf mefSoamLmCurrentStatsElapsedTime {
        type smiv2:TimeInterval;
        description 
         "The time that the current Measurement Interval has been running, in 0.01
          seconds.";
        reference   
         "[MEF SOAM-PM] R24, R87, R112";
      }

      leaf mefSoamLmCurrentStatsSuspect {
        type smiv2:TruthValue;
        description 
         "Whether the Measurement Interval has been marked as suspect.
          
          The object is set to false at the start of a measurement
          interval. It is set to true when there is a discontinuity in the 
          performance measurements during the Measurement Interval.  Conditions
          for a discontinuity include, but are not limited to the following:
          
          1 - The local time-of-day clock is adjusted by at least 10 seconds
          2 - The conducting of a performance measurement is halted before the
              current Measurement Interval is completed
          3 - A local test, failure, or reconfiguration that disrupts service";
        reference   
         "[MEF SOAM-PM] R39, R40, R41";
      }

      leaf mefSoamLmCurrentStatsForwardTransmittedFrames {
        type yang:gauge32;
        description 
         "This object contains the number of frames transmitted in the 
          forward direction by this MEP.
          
          For a PM Session of types lmLmm and lmCcm this includes Ethernet 
          Service Frames and SOAM PDUs that are in a higher MEG level only.
          
          For a PM Session of type lmSlm this includes the count of SOAM 
          ETH-SLM frames only.";
        reference   
         "[MEF SOAM-PM] R69, R87, R112";
      }

      leaf mefSoamLmCurrentStatsForwardReceivedFrames {
        type yang:gauge32;
        description 
         "This object contains the number of frames received in the
          forward direction by this MEP. 
          
          For a PM Session of types lmLmm and lmCcm this includes Ethernet 
          Service Frames and SOAM PDUs that are in a higher MEG level only.
          
          For a PM Session of types lmSlm this includes the count of SOAM 
          ETH-SLM frames only.";
        reference   
         "[MEF SOAM-PM] R69, R87, R112";
      }

      leaf mefSoamLmCurrentStatsForwardMinFlr {
        type uint32 {
          range "0..100000";
        }
        units "milli-percent";
        description 
         "This object contains the minimum one-way frame loss
          ratio in the forward direction calculated by this MEP for this
          Measurement Interval. The FLR value is a ratio that is expressed as a 
          percent with a value of 0 (ratio 0.00) through 100000 (ratio 1.00).
          
          Units are in milli-percent, where 1 indicates 0.001 percent.";
        reference   
         "[MEF SOAM-PM] D37";
      }

      leaf mefSoamLmCurrentStatsForwardMaxFlr {
        type uint32 {
          range "0..100000";
        }
        units "milli-percent";
        description 
         "This object contains the maximum one-way frame loss
          ratio in the forward direction calculated by this MEP for this
          Measurement Interval. The FLR value is a ratio that is expressed as a 
          percent with a value of 0 (ratio 0.00) through 100000 (ratio 1.00).
          
          Units are in milli-percent, where 1 indicates 0.001 percent.";
        reference   
         "[MEF SOAM-PM] D37";
      }

      leaf mefSoamLmCurrentStatsForwardAvgFlr {
        type uint32 {
          range "0..100000";
        }
        units "milli-percent";
        description 
         "This object contains the average one-way frame loss
          ratio in the forward direction calculated by this MEP for this
          Measurement Interval. The FLR value is a ratio that is expressed as a 
          percent with a value of 0 (ratio 0.00) through 100000 (ratio 1.00).
          
          Units are in milli-percent, where 1 indicates 0.001 percent.";
        reference   
         "[MEF SOAM-PM] D37";
      }

      leaf mefSoamLmCurrentStatsBackwardTransmittedFrames {
        type yang:gauge32;
        description 
         "This object contains the number of frames transmitted in the
          backward direction by this MEP.
          
          For a PM Session of type lmLmm and lmCcm this includes Ethernet 
          Service Frames and SOAM PDUs that are in a higher MEG level only.
          
          For a PM Session of type lmSlm this includes the count of SOAM 
          ETH-SLM frames only.";
        reference   
         "[MEF SOAM-PM] R69, R87, R112";
      }

      leaf mefSoamLmCurrentStatsBackwardReceivedFrames {
        type yang:gauge32;
        description 
         "This object contains the number of frames received in the 
          backward direction by this MEP.
          
          For a PM Session of type lmLmm this includes Ethernet 
          Service Frames and SOAM PDUs that are in a higher MEG level only.
          
          For a PM Session of type lmSlm this includes the count of SOAM 
          ETH-SLM frames only.";
        reference   
         "[MEF SOAM-PM] R69, R87, R112";
      }

      leaf mefSoamLmCurrentStatsBackwardMinFlr {
        type uint32 {
          range "0..100000";
        }
        units "milli-percent";
        description 
         "This object contains the minimum one-way frame loss
          ratio in the backward direction calculated by this MEP for 
          this Measurement Interval. The FLR value is a ratio that is expressed as a 
          percent with a value of 0 (ratio 0.00) through 100000 (ratio 1.00).
          
          Units are in milli-percent, where 1 indicates 0.001 percent.";
        reference   
         "[MEF SOAM-PM] D37";
      }

      leaf mefSoamLmCurrentStatsBackwardMaxFlr {
        type uint32 {
          range "0..100000";
        }
        units "milli-percent";
        description 
         "This object contains the maximum one-way frame loss
          ratio in the backward direction calculated by this MEP for 
          this Measurement Interval. The FLR value is a ratio that is expressed 
          as a percent with a value of 0 (ratio 0.00) through 100000 (ratio 1.00).
          
          Units are in milli-percent, where 1 indicates 0.001 percent.";
        reference   
         "[MEF SOAM-PM] D37";
      }

      leaf mefSoamLmCurrentStatsBackwardAvgFlr {
        type uint32 {
          range "0..100000";
        }
        units "milli-percent";
        description 
         "This object contains the average one-way frame loss
          ratio in the backward direction calculated by this MEP for 
          this Measurement Interval. The FLR value is a ratio that is expressed as a 
          percent with a value of 0 (ratio 0.00) through 100000 (ratio 1.00).
          
          Units are in milli-percent, where 1 indicates 0.001 percent.";
        reference   
         "[MEF SOAM-PM] D37";
      }

      leaf mefSoamLmCurrentStatsSoamPdusSent {
        type yang:gauge32;
        description 
         "This object contains the count of the number of SOAM PDUs sent 
          during this Measurement Interval. 
          
          This object applies when mefSoamLmCfgType is lmLmm, lmSlm, or 
          lmCcm. It indicates the number of LMM, CCM, or SLM SOAM frames 
          transmitted.";
        reference   
         "[MEF SOAM-PM] R69, R87, R112";
      }

      leaf mefSoamLmCurrentStatsSoamPdusReceived {
        type yang:gauge32;
        description 
         "This object contains the count of the number of SOAM PDUs
          PDUs received in this Measurement Interval.
          
          This object applies when mefSoamLmCfgType is lmLmm, lmSlm, or 
          lmCcm. This object indicates the number of LMR, CCM, or SLR SOAM
          frames received.";
        reference   
         "[MEF SOAM-PM] R69, R87, R112";
      }
    }


    /* XXX table comments here XXX */

    list mefSoamLmHistoryAvailStatsEntry {

      key "dot1agCfmMdIndex dot1agCfmMaIndex 
           dot1agCfmMepIdentifier mefSoamLmCfgIndex 
           mefSoamLmHistoryAvailStatsIndex";
      description   
       "The conceptual row of mefSoamLmHistoryAvailStatsTable";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        config true;
        description 
         "Automagically generated leafref leaf.";
      }

      leaf mefSoamLmHistoryAvailStatsIndex {
        type uint32;
        description 
         "The index for the availability Measurement Interval within this
          PM session.
          
          Measurement Interval indexes are assigned sequentially by
          the SNMP Agent.  The first Measurement Interval that occurs after
          the session is started is assigned index 1.  Measurement Intervals
          for availability (stored in this table) are based on 
          mefSoamLmCfgAvailabilityMeasurementInterval and are indexed independently
          of Measurement Intervals for FLR (stored in mefSoamLmHistoryStatsTable).
          
          Referential integrity is necessary, i.e., the index needs to be
          persistent upon a reboot or restart of a device.  The index
          is never reused while this session is active until it wraps to zero.
          The index value keeps increasing up to that time.";
      }

      leaf mefSoamLmHistoryAvailStatsEndTime {
        type smiv2:DateAndTime;
        description 
         "The time that the Measurement Interval ended.";
        reference   
         "[MEF SOAM-PM] R23, R87, R112";
      }

      leaf mefSoamLmHistoryAvailStatsElapsedTime {
        type smiv2:TimeInterval;
        description 
         "The length of time that the Measurement Interval ran for,
          in 0.01 seconds.";
        reference   
         "[MEF SOAM-PM] R24, R87, R112";
      }

      leaf mefSoamLmHistoryAvailStatsSuspect {
        type smiv2:TruthValue;
        description 
         "Whether the Measurement Interval has been marked as suspect.
          
          The object is set to true when there is a discontinuity in the 
          performance measurements during the Measurement Interval.  Conditions
          for a discontinuity include, but are not limited to the following:
          
          1 - The local time-of-day clock is adjusted by at least 10 seconds
          2 - The conducting of a performance measurement is halted before the
              current Measurement Interval is completed
          3 - A local test, failure, or reconfiguration that disrupts service";
        reference   
         "[MEF SOAM-PM] R39, R40, R41, R42";
      }

      leaf mefSoamLmHistoryAvailStatsForwardHighLoss {
        type uint32;
        description 
         "This object is the number of high loss intervals (HLI) over
          time in the forward direction. 
          
          The value starts at 0 and increments for every HLI that occurs.
          This parameter is equivalent to 'L Sub T' found in MEF 10.2.1.";
        reference   
         "[MEF 10.2.1] 6.9.9; [MEF SOAM-PM] R87";
      }

      leaf mefSoamLmHistoryAvailStatsBackwardHighLoss {
        type uint32;
        description 
         "This object is the number of high loss intervals (HLI) over
          time in the backward direction. 
          
          The value starts at 0 and increments for every HLI that occurs.
          This parameter is equivalent to 'L Sub T' found in MEF 10.2.1.";
        reference   
         "[MEF 10.2.1] 6.9.9; [MEF SOAM-PM] R87";
      }

      leaf mefSoamLmHistoryAvailStatsForwardConsecutiveHighLoss {
        type uint32;
        description 
         "This object is the number of consecutive high loss intervals
          (CHLI) over time in the forward direction. 
          
          The value starts at 0 and increments for every HLI that occurs 
          that is determined to fall within a CHLI.
          This parameter is equivalent to 'B Sub T' found in MEF 10.2.1.";
        reference   
         "[MEF 10.2.1] 6.9.9; [MEF SOAM-PM] R87";
      }

      leaf mefSoamLmHistoryAvailStatsBackwardConsecutiveHighLoss {
        type uint32;
        description 
         "This object is the number of consecutive high loss intervals
          (CHLI) over time in the forward direction. 
          
          The value starts at 0 and increments for every HLI that occurs
          that is determined to fall within a CHLI.
          This parameter is equivalent to 'B Sub T' found in MEF 10.2.1.";
        reference   
         "[MEF 10.2.1] 6.9.9; [MEF SOAM-PM] R87";
      }

      leaf mefSoamLmHistoryAvailStatsForwardAvailable {
        type yang:gauge32;
        description 
         "This object contains the number of availability indicators 
          evaluated as available in the forward direction by this MEP during
          this Measurement Interval.";
        reference   
         "[MEF SOAM-PM] R87; [MEF 10.2.1]";
      }

      leaf mefSoamLmHistoryAvailStatsBackwardAvailable {
        type yang:gauge32;
        description 
         "This object contains the number of availability indicators 
          evaluated as available in the backward direction by this MEP during
          this Measurement Interval.";
        reference   
         "[MEF SOAM-PM] R87";
      }

      leaf mefSoamLmHistoryAvailStatsForwardUnavailable {
        type yang:gauge32;
        description 
         "This object contains the number of availability indicators 
          evaluated as unavailable in the forward direction by this MEP during
          this Measurement Interval.";
        reference   
         "[MEF SOAM-PM] R87";
      }

      leaf mefSoamLmHistoryAvailStatsBackwardUnavailable {
        type yang:gauge32;
        description 
         "This object contains the number of availability indicators 
          evaluated as unavailable in the backward direction by this MEP
          during this Measurement Interval.";
        reference   
         "[MEF SOAM-PM] R87";
      }

      leaf mefSoamLmHistoryAvailStatsForwardMinFlr {
        type uint32 {
          range "0..100000";
        }
        units "milli-percent";
        description 
         "This object contains the minimum one-way availability flr in the forward
          direction, from among the set of availability flr values calculated by
          the MEP in this Measurement Interval.  There is one availability flr 
          value for each 'delta_t' time period within the Measurement Interval, as
          specified in MEF 10.2.1.
          
          The flr value is a ratio that is expressed as a 
          percent with a value of 0 (ratio 0.00) through 100000 (ratio 1.00).
          
          Units are in milli-percent, where 1 indicates 0.001 percent.";
        reference   
         "[MEF SOAM-PM] D37";
      }

      leaf mefSoamLmHistoryAvailStatsForwardMaxFlr {
        type uint32 {
          range "0..100000";
        }
        units "milli-percent";
        description 
         "This object contains the maximum one-way availability flr in the forward
          direction, from among the set of availability flr values calculated by
          the MEP in this Measurement Interval.  There is one availability flr 
          value for each 'delta_t' time period within the Measurement Interval, as
          specified in MEF 10.2.1.
          
          The flr value is a ratio that is expressed as a 
          percent with a value of 0 (ratio 0.00) through 100000 (ratio 1.00).
          
          Units are in milli-percent, where 1 indicates 0.001 percent.";
        reference   
         "[MEF SOAM-PM] D37";
      }

      leaf mefSoamLmHistoryAvailStatsForwardAvgFlr {
        type uint32 {
          range "0..100000";
        }
        units "milli-percent";
        description 
         "This object contains the average one-way availability flr in the forward
          direction, from among the set of availability flr values calculated by
          the MEP in this Measurement Interval.  There is one availability flr 
          value for each 'delta_t' time period within the Measurement Interval, as
          specified in MEF 10.2.1.
          
          The flr value is a ratio that is expressed as a 
          percent with a value of 0 (ratio 0.00) through 100000 (ratio 1.00).
          
          Units are in milli-percent, where 1 indicates 0.001 percent.";
        reference   
         "[MEF SOAM-PM] D37";
      }

      leaf mefSoamLmHistoryAvailStatsBackwardMinFlr {
        type uint32 {
          range "0..100000";
        }
        units "milli-percent";
        description 
         "This object contains the minimum one-way availability flr in the backward
          direction, from among the set of availability flr values calculated by
          the MEP in this Measurement Interval.  There is one availability flr 
          value for each 'delta_t' time period within the Measurement Interval, as
          specified in MEF 10.2.1.
          
          The flr value is a ratio that is expressed as a 
          percent with a value of 0 (ratio 0.00) through 100000 (ratio 1.00).
          
          Units are in milli-percent, where 1 indicates 0.001 percent.";
        reference   
         "[MEF SOAM-PM] D37";
      }

      leaf mefSoamLmHistoryAvailStatsBackwardMaxFlr {
        type uint32 {
          range "0..100000";
        }
        units "milli-percent";
        description 
         "This object contains the maximum one-way availability flr in the backward
          direction, from among the set of availability flr values calculated by
          the MEP in this Measurement Interval.  There is one availability flr 
          value for each 'delta_t' time period within the Measurement Interval, as
          specified in MEF 10.2.1.
          
          The flr value is a ratio that is expressed 
          as a percent with a value of 0 (ratio 0.00) through 100000 (ratio 1.00).
          
          Units are in milli-percent, where 1 indicates 0.001 percent.";
        reference   
         "[MEF SOAM-PM] D37";
      }

      leaf mefSoamLmHistoryAvailStatsBackwardAvgFlr {
        type uint32 {
          range "0..100000";
        }
        units "milli-percent";
        description 
         "This object contains the average one-way availability flr in the backward
          direction, from among the set of availability flr values calculated by
          the MEP in this Measurement Interval.  There is one availability flr 
          value for each 'delta_t' time period within the Measurement Interval, as
          specified in MEF 10.2.1.
          
          The flr value is a ratio that is expressed as a 
          percent with a value of 0 (ratio 0.00) through 100000 (ratio 1.00).
          
          Units are in milli-percent, where 1 indicates 0.001 percent.";
        reference   
         "[MEF SOAM-PM] D37";
      }
    }


    /* XXX table comments here XXX */

    list mefSoamLmHistoryStatsEntry {

      key "dot1agCfmMdIndex dot1agCfmMaIndex 
           dot1agCfmMepIdentifier mefSoamLmCfgIndex 
           mefSoamLmHistoryStatsIndex";
      description   
       "The conceptual row of mefSoamLmHistoryStatsTable";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        config true;
        description 
         "Automagically generated leafref leaf.";
      }

      leaf mefSoamLmHistoryStatsIndex {
        type uint32;
        description 
         "The index for the Measurement Interval within this
          PM session.
          
          Measurement Interval indexes are assigned sequentially by
          the SNMP Agent.  The first Measurement Interval that occurs after
          the session is started is assigned index 1. Measurement Intervals
          for FLR (stored in this table) are based on 
          mefSoamLmCfgMeasurementInterval and are indexed independently
          of Measurement Intervals for availability (stored in 
          mefSoamLmHistoryAvailStatsTable).
          
          Referential integrity is necessary, i.e., the index needs to be
          persistent upon a reboot or restart of a device.  The index
          is never reused while this session is active until it wraps to zero.
          The index value keeps increasing up to that time.";
      }

      leaf mefSoamLmHistoryStatsEndTime {
        type smiv2:DateAndTime;
        description 
         "The time that the Measurement Interval ended.";
        reference   
         "[MEF SOAM-PM] R23, R87, R112";
      }

      leaf mefSoamLmHistoryStatsElapsedTime {
        type smiv2:TimeInterval;
        description 
         "The length of time that the Measurement Interval ran for,
          in 0.01 seconds.";
        reference   
         "[MEF SOAM-PM] R24, R87, R112";
      }

      leaf mefSoamLmHistoryStatsSuspect {
        type smiv2:TruthValue;
        description 
         "Whether the Measurement Interval has been marked as suspect.
          
          The object is set to true when there is a discontinuity in the 
          performance measurements during the Measurement Interval.  Conditions
          for a discontinuity include, but are not limited to the following:
          
          1 - The local time-of-day clock is adjusted by at least 10 seconds
          2 - The conducting of a performance measurement is halted before the
              current Measurement Interval is completed
          3 - A local test, failure, or reconfiguration that disrupts service";
        reference   
         "[MEF SOAM-PM] R39, R40, R41, R42";
      }

      leaf mefSoamLmHistoryStatsForwardTransmittedFrames {
        type yang:gauge32;
        description 
         "This object contains the number of frames transmitted in the 
          forward direction by this MEP. 
          
          For a PM Session of types lmLmm and lmCcm this includes Ethernet 
          Service Frames and SOAM PDUs that are in a higher MEG level only.
          
          For a PM Session of type lmSlm this includes the count of OAM 
          ETH-SLM frames only.";
        reference   
         "[MEF SOAM-PM] R69, R87, R112";
      }

      leaf mefSoamLmHistoryStatsForwardReceivedFrames {
        type yang:gauge32;
        description 
         "This object contains the number of frames received in the
          forward direction by this MEP. 
          
          For a PM Session of types lmLmm and lmCcm this includes Ethernet 
          Service Frames and SOAM PDUs that are in a higher MEG level only.
          
          For a PM Session of type lmSlm this includes the count of OAM 
          ETH-SLM frames only.";
        reference   
         "[MEF SOAM-PM] R69, R87, R112";
      }

      leaf mefSoamLmHistoryStatsForwardMinFlr {
        type uint32 {
          range "0..100000";
        }
        units "milli-percent";
        description 
         "This object contains the minimum one-way frame loss
          ratio in the forward direction calculated by this MEP for this
          Measurement Interval. The FLR value is a ratio that is expressed as a 
          percent with a value of 0 (ratio 0.00) through 100000 (ratio 1.00).
          
          Units are in milli-percent, where 1 indicates 0.001 percent.";
        reference   
         "[MEF SOAM-PM] D37";
      }

      leaf mefSoamLmHistoryStatsForwardMaxFlr {
        type uint32 {
          range "0..100000";
        }
        units "milli-percent";
        description 
         "This object contains the maximum one-way frame loss
          ratio in the forward direction calculated by this MEP for this
          Measurement Interval. The FLR value is a ratio that is expressed as a 
          percent with a value of 0 (ratio 0.00) through 100000 (ratio 1.00).
          
          Units are in milli-percent, where 1 indicates 0.001 percent.";
        reference   
         "[MEF SOAM-PM] D37";
      }

      leaf mefSoamLmHistoryStatsForwardAvgFlr {
        type uint32 {
          range "0..100000";
        }
        units "milli-percent";
        description 
         "This object contains the average one-way frame loss
          ratio in the forward direction calculated by this MEP for this
          Measurement Interval. The FLR value is a ratio that is expressed as a 
          percent with a value of 0 (ratio 0.00) through 100000 (ratio 1.00).
          
          Units are in milli-percent, where 1 indicates 0.001 percent.";
        reference   
         "[MEF SOAM-PM] D37";
      }

      leaf mefSoamLmHistoryStatsBackwardTransmittedFrames {
        type yang:gauge32;
        description 
         "This object contains the number of frames transmitted in the
          backward direction by this MEP.
          
          For a PM Session of type lmLmm and lmCcm this includes Ethernet 
          Service Frames and SOAM PDUs that are in a higher MEG level only.
          
          For a PM Session of types lmSlm this includes the count of SOAM 
          ETH-SLM frames only.";
        reference   
         "[MEF SOAM-PM] D37";
      }

      leaf mefSoamLmHistoryStatsBackwardReceivedFrames {
        type yang:gauge32;
        description 
         "This object contains the number of frames received in the 
          backward direction by this MEP.
          
          For a PM Session of type lmLmm and lmCcm this includes Ethernet 
          Service Frames and SOAM PDUs that are in a higher MEG level only.
          
          For a PM Session of types lmSlm this includes the count of SOAM 
          ETH-SLM frames only.";
        reference   
         "[MEF SOAM-PM] R69, R87, R112";
      }

      leaf mefSoamLmHistoryStatsBackwardMinFlr {
        type uint32 {
          range "0..100000";
        }
        units "milli-percent";
        description 
         "This object contains the minimum one-way frame loss
          ratio in the backward direction calculated by this MEP for 
          this Measurement Interval. The FLR value is a ratio that is expressed as a 
          percent with a value of 0 (ratio 0.00) through 100000 (ratio 1.00).
          
          Units are in milli-percent, where 1 indicates 0.001 percent.";
        reference   
         "[MEF SOAM-PM] R69, R87, R112";
      }

      leaf mefSoamLmHistoryStatsBackwardMaxFlr {
        type uint32 {
          range "0..100000";
        }
        units "milli-percent";
        description 
         "This object contains the maximum one-way frame loss
          ratio in the backward direction calculated by this MEP for 
          this Measurement Interval. The FLR value is a ratio that is expressed as a 
          percent with a value of 0 (ratio 0.00) through 100000 (ratio 1.00).
          
          Units are in milli-percent, where 1 indicates 0.001 percent.";
        reference   
         "[MEF SOAM-PM] D37";
      }

      leaf mefSoamLmHistoryStatsBackwardAvgFlr {
        type uint32 {
          range "0..100000";
        }
        units "milli-percent";
        description 
         "This object contains the average one-way frame loss
          ratio in the backward direction calculated by this MEP for 
          this Measurement Interval. The FLR value is a ratio that is expressed as a 
          percent with a value of 0 (ratio 0.00) through 100000 (ratio 1.00).
          
          Units are in milli-percent, where 1 indicates 0.001 percent.";
        reference   
         "[MEF SOAM-PM] D37";
      }

      leaf mefSoamLmHistoryStatsSoamPdusSent {
        type yang:gauge32;
        description 
         "This object contains the count of the number of SOAM PDUs sent 
          during this Measurement Interval.
          
          This object applies when mefSoamLmCfgType is lmLmm, lmSlm, 
          or lmCcm. It indicates the number of LMM, CCM, or SLM SOAM frames 
          transmitted.";
        reference   
         "[MEF SOAM-PM] R69, R87";
      }

      leaf mefSoamLmHistoryStatsSoamPdusReceived {
        type yang:gauge32;
        description 
         "This object contains the count of the number of SOAM
          PDUs received in this Measurement Interval.
          
          This object applies when mefSoamLmCfgType is lmLmm, lmSlm, 
          or lmCcm. This object indicates the number of LMR, CCM, or SLR
          SOAM frames received.";
        reference   
         "[MEF SOAM-PM] R69, R87";
      }
    }


    /* XXX table comments here XXX */

    list mefSoamLmThresholdCfgEntry {

      key "dot1agCfmMdIndex dot1agCfmMaIndex 
           dot1agCfmMepIdentifier mefSoamLmCfgIndex 
           mefSoamLmThresholdCfgIndex";
      description   
       "The conceptual row of mefSoamLmThresholdCfgTable.";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        config true;
        description 
         "Automagically generated leafref leaf.";
      }

      leaf mefSoamLmThresholdCfgIndex {
        type uint32 {
          range "1..4294967295";
        }
        description 
         "The index of the threshold number for the specific LM
          threshold entry. 
          
          An index value of '1' needs to be supported. Other index values
          can also be supported.";
      }

      leaf mefSoamLmThresholdCfgEnable {
        type bits {
          bit bMefSoamLmMeasuredFlrForwardThreshold          { position 0; }
          bit bMefSoamLmMaxFlrForwardThreshold               { position 1; }
          bit bMefSoamLmAvgFlrForwardThreshold               { position 2; }
          bit bMefSoamLmMeasuredFlrBackwardThreshold         { position 3; }
          bit bMefSoamLmMaxFlrBackwardThreshold              { position 4; }
          bit bMefSoamLmAvgFlrBackwardThreshold              { position 5; }
          bit bMefSoamLmForwardHighLossThreshold             { position 6; }
          bit bMefSoamLmForwardConsecutiveHighLossThreshold  { position 7; }
          bit bMefSoamLmBackwardHighLossThreshold            { position 8; }
          bit bMefSoamLmBackwardConsecutiveHighLossThreshold { position 9; }
          bit bMefSoamLmUnavailForwardThreshold              { position 10; }
          bit bMefSoamLmAvailRatioForwardThreshold           { position 11; }
          bit bMefSoamLmUnavailBackwardThreshold             { position 12; }
          bit bMefSoamLmAvailRatioBackwardThreshold          { position 13; }
        }
        config true;
        description 
         "A vector of bits that indicates the type of SOAM LM thresholds
          notifications that are enabled. 
          
          A bit set to '1' enables the specific SOAM LM threshold notification 
          and when the specific counter is enabled and the threshold is crossed a
          notification is generated. 
          
          A bit set to '0' disables the specific SOAM LM threshold notification.
          
          If a particular SOAM LM threshold is not supported the BIT value is
          set to '0'.
          
          bMefSoamLmMeasuredFlrForwardThreshold(0)
                  Enables/disables measured frame loss forward ratio threshold 
                  notification. The notification is sent immediately when the
                  mefSoamLmMeasuredStatsForwardFlr value is 
                  greater than or equal to the threshold value.
          bMefSoamLmMaxFlrForwardThreshold(1)
                  Enables/disables maximum frame loss forward ratio threshold 
                  notification. The notification is sent immediately when the
                  mefSoamLmCurrentStatsForwardMaxFlr value is greater
                  than or equal to threshold value in a Measurement Interval.
          bMefSoamLmAvgFlrForwardThreshold(2)
                  Enables/disables average frame loss forward ratio threshold
                  notification. The notification is sent when at the end of a
                  Measurement Interval if the 
                  mefSoamLmCurrentStatsForwardAvgFlr value is greater
                  than or equal to the threshold value.
          bMefSoamLmMeasuredFlrBackwardThreshold(3)
                  Enables/disables measured frame loss backward ratio threshold 
                  notification. The notification is sent immediately when the
                  mefSoamLmMeasuredStatsBackwardFlr value is 
                  greater than or equal to the threshold value.
          bMefSoamLmMaxFlrBackwardThreshold(4)
                  Enables/disables maximum frame loss backward ratio threshold 
                  notification. The notification is sent immediately when the
                  mefSoamLmCurrentStatsBackwardMaxFlr value is greater
                  than or equal to threshold value in a Measurement Interval.
          bMefSoamLmAvgFlrBackwardThreshold(5)
                  Enables/disables average frame loss backward ratio threshold
                  notification. The notification is sent when at the end of a
                  Measurement Interval if the 
                  mefSoamLmCurrentStatsBackwardAvgFlr value is
                  greater than or equal to the threshold value.
          bMefSoamLmForwardHighLossThreshold(6)
                  Enables/disables forward high loss threshold
                  notification. The notification is sent immediately when the 
                  mefSoamLmCurrentAvailStatsForwardHighLoss value is
                  greater than or equal to the threshold value in a measurement
                  interval.
          bMefSoamLmForwardConsecutiveHighLossThreshold(7)
                  Enables/disables forward consecutive high loss threshold
                  notification. The notification is sent immediately when the 
                  mefSoamLmCurrentAvailStatsForwardConsecutiveHighLoss value is
                  greater than or equal to the threshold value in a measurement
                  interval.
          bMefSoamLmBackwardHighLossThreshold(8)
                  Enables/disables backward high loss threshold
                  notification. The notification is sent immediately when the 
                  mefSoamLmCurrentAvailStatsBackwardHighLoss value is
                  greater than or equal to the threshold value in a measurement
                  interval.
          bMefSoamLmBackwardConsecutiveHighLossThreshold(9)
                  Enables/disables backward consecutive high loss threshold
                  notification. The notification is sent immediately when the 
                  mefSoamLmCurrentAvailStatsBackwardConsecutiveHighLoss value is
                  greater than or equal to the threshold value in a measurement
                  interval.
          bMefSoamLmUnavailForwardThreshold(10)
                  Enables/disables unavailable forward threshold 
                  notification. The notification is sent immediately when the
                  mefSoamLmCurrentAvailStatsForwardUnavailable value is 
                  greater than or equal to threshold value in a Measurement Interval.
          bMefSoamLmAvailRatioForwardThreshold(11)
                  Enables/disables availability ratio forward threshold 
                  notification. The notification is sent immediately when the
                  availability ratio is greater than or equal to threshold value
                  in a Measurement Interval.  The availability ratio can be calculated
                  from the values of mefSoamLmCurrentAvailStatsForwardAvailable and
                  mefSoamLmCurrentAvailStatsForwardUnavailable.
          bMefSoamLmUnavailBackwardThreshold(12)
                  Enables/disables unavailable backward threshold 
                  notification. The notification is sent immediately when the
                  mefSoamLmCurrentAvailStatsBackwardUnavailable value is 
                  greater than or equal to threshold value in a Measurement Interval.
          bMefSoamLmAvailRatioBackwardThreshold(13)
                  Enables/disables availability ratio backward threshold 
                  notification. The notification is sent immediately when the
                  availability ratio is greater than or equal to threshold value
                  in a Measurement Interval.  The availability ratio can be calculated
                  from the values of mefSoamLmCurrentAvailStatsBackwardAvailable and
                  mefSoamLmCurrentAvailStatsBackwardUnavailable.";
      }

      leaf mefSoamLmThresholdCfgMeasuredFlrForwardThreshold {
        type uint32 {
          range "0..100000";
        }
        units "milli-percent";
        config true;
        description 
         "This object is used to set the measured forward frame loss ratio
          threshold value that will be used to determine if a threshold 
          notification is generated.";
      }

      leaf mefSoamLmThresholdCfgMaxFlrForwardThreshold {
        type uint32 {
          range "0..100000";
        }
        units "milli-percent";
        config true;
        description 
         "This object is used to set the maximum forward frame loss ratio
          threshold value that will be used to determine if a threshold 
          notification is generated.";
      }

      leaf mefSoamLmThresholdCfgAvgFlrForwardThreshold {
        type uint32 {
          range "0..100000";
        }
        units "milli-percent";
        config true;
        description 
         "This object is used to set the average forward frame loss ratio
          threshold value that will be used to determine if a threshold 
          notification is generated.";
      }

      leaf mefSoamLmThresholdCfgMeasuredFlrBackwardThreshold {
        type uint32 {
          range "0..100000";
        }
        units "milli-percent";
        config true;
        description 
         "This object is used to set the measured backward frame loss ratio
          threshold value that will be used to determine if a threshold 
          notification is generated.";
      }

      leaf mefSoamLmThresholdCfgMaxFlrBackwardThreshold {
        type uint32 {
          range "0..100000";
        }
        units "milli-percent";
        config true;
        description 
         "This object is used to set the maximum backward frame loss ratio
          threshold value that will be used to determine if a threshold 
          notification is generated.";
      }

      leaf mefSoamLmThresholdCfgAvgFlrBackwardThreshold {
        type uint32 {
          range "0..100000";
        }
        units "milli-percent";
        config true;
        description 
         "This object is used to set the average backward frame loss ratio
          threshold value that will be used to determine if a threshold 
          notification is generated.";
      }

      leaf mefSoamLmThresholdCfgForwardHighLossThreshold {
        type uint32;
        config true;
        description 
         "This object is used to set the forward high loss threshold value that
          will be used to determine if a threshold notification is generated.";
      }

      leaf mefSoamLmThresholdCfgForwardConsecutiveHighLossThreshold {
        type uint32;
        config true;
        description 
         "This object is used to set the consecutive forward high loss
          threshold value that will be used to determine if a threshold
          notification is generated.";
      }

      leaf mefSoamLmThresholdCfgBackwardHighLossThreshold {
        type uint32;
        config true;
        description 
         "This object is used to set the backward high loss threshold value that
          will be used to determine if a threshold notification is generated.";
      }

      leaf mefSoamLmThresholdCfgBackwardConsecutiveHighLossThreshold {
        type uint32;
        config true;
        description 
         "This object is used to set the consecutive backward high loss
          threshold value that will be used to determine if a threshold
          notification is generated.";
      }

      leaf mefSoamLmThresholdCfgForwardUnavailCountThreshold {
        type uint32;
        config true;
        description 
         "This object is used to set the forward unavailability 
          threshold value that will be used to determine if a threshold 
          notification is generated.";
      }

      leaf mefSoamLmThresholdCfgForwardAvailRatioThreshold {
        type uint32 {
          range "0..100000";
        }
        units "milli-percent";
        config true;
        description 
         "This object is used to set the forward availability/total time
          ratio threshold value that will be used to determine if a threshold 
          notification is generated if the ratio drops below the configured
          value.
          
          The ratio value is expressed as a percent with a value of 0 (ratio 
          0.00) through 100000 (ratio 1.00) 
          
          Units are in milli-percent, where 1 indicates 0.001 percent.";
      }

      leaf mefSoamLmThresholdCfgBackwardUnavailCountThreshold {
        type uint32;
        config true;
        description 
         "This object is used to set the backward unavailability 
          threshold value that will be used to determine if a threshold 
          notification is generated.";
      }

      leaf mefSoamLmThresholdCfgBackwardAvailRatioThreshold {
        type uint32 {
          range "0..100000";
        }
        units "milli-percent";
        config true;
        description 
         "This object is used to set the backward availability/total time
          ratio threshold value that will be used to determine if a threshold 
          notification is generated if the ratio drops below the configured
          value.
          
          The ratio value is expressed as a percent with a value of 0 (ratio 
          0.00) through 100000 (ratio 1.00) 
          
          Units are in milli-percent, where 1 indicates 0.001 percent.";
      }

      leaf mefSoamLmThresholdCfgRowStatus {
        type smiv2:RowStatus;
        config true;
        description 
         "The status of the row.
          
          The writable columns in a row cannot be changed if the row
          is active. All columns are to have a valid value before a row
          can be activated.";
      }
    }
  }

  container mefSoamPmDmObjects {


    /* XXX table comments here XXX */

    list mefSoamDmCfgEntry {

      key "dot1agCfmMdIndex dot1agCfmMaIndex 
           dot1agCfmMepIdentifier mefSoamDmCfgIndex";
      description   
       "The conceptual row of mefSoamDmCfgTable.";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }

      leaf mefSoamDmCfgIndex {
        type uint32 {
          range "1..4294967295";
        }
        description 
         "An index to the Delay Measurement Configuration table which indicates
          the specific measurement session for the MEP.
          
          mefSoamPmMepOperNextIndex needs to be inspected to find an
          available index for row-creation.
          
          Referential integrity is necessary, i.e., the index needs to be
          persistent upon a reboot or restart of a device.  The index
          is never reused for other PM sessions on the same MEP while this
          session is active.  The index value keeps increasing until it
          wraps to zero. This is to facilitate access control based
          on a fixed index for an EMS, since the index is not reused.";
      }

      leaf mefSoamDmCfgType {
        type enumeration {
          enum dmDmm   { value 1; }
          enum dm1DmTx { value 2; }
          enum dm1DmRx { value 3; }
        }
        config true;
        description 
         "This object indicates what type of Delay Measurement is to
          be performed.
          
          dmDmm(1)         DMM SOAM PDU generated, DMR responses received 
                           (one-way or two-way measurements)
          dm1DmTx(2)       1DM SOAM PDU generated (one-way measurements are made by
                           the receiver)
          dm1DmRx(3)       1DM SOAM PDU received and tracked (one-way measurements)
          
          The exact PDUs to use are specified by this object in combination with
          mefSoamDmCfgVersion.
          
          The value dmDMM is required. The values dm1DmTx and dm1DmRx are optional.
          
          This object can only be written at row creation time and cannot be 
          modified once it has been created.";
        reference   
         "[MEF SOAM-PM] R52, R53, R54, O5, R88";
      }

      leaf mefSoamDmCfgVersion {
        type uint32;
        config true;
        description 
         "This object indicates the version of the PDUs used to perform 
          Delay Measurement.
          
          Version 0 indicates the PDU formats defined in Y.1731-2008.
          Version 1 indicates the PDU formats defined in Y.1731-2011.
          
          The exact PDUs to use are specified by this object in combination with
          mefSoamDmCfgType.
          
          This object can only be written at row creation time and cannot be 
          modified once it has been created.";
        reference   
         "[Y.1731]";
      }

      leaf mefSoamDmCfgEnabled {
        type smiv2:TruthValue;
        config true;
        description 
         "This object specifies whether the Delay Measurement session is
          enabled. 
          
          The value 'true' indicates the Delay Measurement session is enabled AND
          SOAM PDUs are sent and/or measurements are collected when the session
          is running according to the scheduling objects (start time, stop time,
          etc.).
          
          The value 'false' indicates the Delay Measurement session is disabled
          AND SOAM PDUs are not sent and/or measurements collected.
          
          For a Delay Measurement session to be removed the row is deleted in 
          order to release internal resources.
          
          This object can written/modified after row creation time.
          
          If the DM session is enabled it resumes after shutdown/restart.
          
          If the DM session is disabled the current Measurement Interval is 
          stopped, if it in process at the time, and all the in process calculations
          for the partially completed Measurement Interval are finalized.
          
          This object does not affect whether the single-ended Responder is
          enabled or not, which is enabled or disabled by the 
          mefSoamPmMepDmSingleEndedResponder object.";
        reference   
         "[MEF SOAM-PM] R4, R5, R6, O1, R12, R14";
      }

      leaf mefSoamDmCfgMeasurementEnable {
        type bits {
          bit bSoamPdusSent                    { position 0; }
          bit bSoamPdusReceived                { position 1; }
          bit bFrameDelayTwoWayBins            { position 2; }
          bit bFrameDelayTwoWayMin             { position 3; }
          bit bFrameDelayTwoWayMax             { position 4; }
          bit bFrameDelayTwoWayAvg             { position 5; }
          bit bFrameDelayForwardBins           { position 6; }
          bit bFrameDelayForwardMin            { position 7; }
          bit bFrameDelayForwardMax            { position 8; }
          bit bFrameDelayForwardAvg            { position 9; }
          bit bFrameDelayBackwardBins          { position 10; }
          bit bFrameDelayBackwardMin           { position 11; }
          bit bFrameDelayBackwardMax           { position 12; }
          bit bFrameDelayBackwardAvg           { position 13; }
          bit bIfdvForwardBins                 { position 14; }
          bit bIfdvForwardMin                  { position 15; }
          bit bIfdvForwardMax                  { position 16; }
          bit bIfdvForwardAvg                  { position 17; }
          bit bIfdvBackwardBins                { position 18; }
          bit bIfdvBackwardMin                 { position 19; }
          bit bIfdvBackwardMax                 { position 20; }
          bit bIfdvBackwardAvg                 { position 21; }
          bit bIfdvTwoWayBins                  { position 22; }
          bit bIfdvTwoWayMin                   { position 23; }
          bit bIfdvTwoWayMax                   { position 24; }
          bit bIfdvTwoWayAvg                   { position 25; }
          bit bFrameDelayRangeForwardBins      { position 26; }
          bit bFrameDelayRangeForwardMax       { position 27; }
          bit bFrameDelayRangeForwardAvg       { position 28; }
          bit bFrameDelayRangeBackwardBins     { position 29; }
          bit bFrameDelayRangeBackwardMax      { position 30; }
          bit bFrameDelayRangeBackwardAvg      { position 31; }
          bit bFrameDelayRangeTwoWayBins       { position 32; }
          bit bFrameDelayRangeTwoWayMax        { position 33; }
          bit bFrameDelayRangeTwoWayAvg        { position 34; }
          bit bMeasuredStatsFrameDelayTwoWay   { position 35; }
          bit bMeasuredStatsFrameDelayForward  { position 36; }
          bit bMeasuredStatsFrameDelayBackward { position 37; }
          bit bMeasuredStatsIfdvTwoWay         { position 38; }
          bit bMeasuredStatsIfdvForward        { position 39; }
          bit bMeasuredStatsIfdvBackward       { position 40; }
        }
        config true;
        description 
         "A vector of bits that indicates the type of SOAM DM counters that
          are enabled. 
          
          A bit set to '1' enables the specific SOAM DM counter.
          
          A bit set to '0' disables the SOAM DM counter.
          
          If a particular SOAM DM counter is not supported the BIT value is
          set to '0'.
          
          Not all SOAM DM counters are supported for all SOAM DM types. 
          
          This object can only be written at row creation time and cannot be 
          modified once it has been created.
          
          bSoamPdusSent(0)
              Enables/disables the mefSoamDmCurrentStatsSoamPdusSent
              and mefSoamDmHistoryStatsSoamPdusSent counters.
          bSoamPdusReceived(1)
              Enables/disables the mefSoamDmCurrentStatsSoamPdusReceived
              and mefSoamDmHistoryStatsSoamPdusReceived counters.
          bFrameDelayTwoWayBins(2)
              Enables/disables the mefSoamDmCurrentStatsBinsEntry counter
              and the mefSoamDmHistoryStatsBinsEntry counter
              when the mefSoamDmCfgMeasBinType is 'twoWayFrameDelay'.
          bFrameDelayTwoWayMin(3)
              Enables/disables the mefSoamDmCurrentStatsFrameDelayTwoWayMin
              and mefSoamDmHistoryStatsFrameDelayTwoWayMin counters.
          bFrameDelayTwoWayMax(4)
              Enables/disables the mefSoamDmCurrentStatsFrameDelayTwoWayMax
              and mefSoamDmHistoryStatsFrameDelayTwoWayMax counters.
          bFrameDelayTwoWayAvg(5)
              Enables/disables the mefSoamDmCurrentStatsFrameDelayTwoWayAvg
              and mefSoamDmHistoryStatsFrameDelayTwoWayAvg counters.
          bFrameDelayForwardBins(6)
              Enables/disables the mefSoamDmCurrentStatsBinsEntry counter
              and the mefSoamDmHistoryStatsBinsEntry counter
              when the mefSoamDmCfgMeasBinType is 'forwardFrameDelay'.
          bFrameDelayForwardMin(7)
              Enables/disables the mefSoamDmCurrentStatsFrameDelayForwardMin
              and mefSoamDmHistoryStatsFrameDelayForwardMin counters.
          bFrameDelayForwardMax(8)
              Enables/disables the mefSoamDmCurrentStatsFrameDelayForwardMax
              and mefSoamDmHistoryStatsFrameDelayForwardMax counters.
          bFrameDelayForwardAvg(9)
              Enables/disables the mefSoamDmCurrentStatsFrameDelayForwardAvg
              and mefSoamDmHistoryStatsFrameDelayForwardAvg counters.
          bFrameDelayBackwardBins(10)
              Enables/disables the mefSoamDmCurrentStatsBinsEntry counter
              and the mefSoamDmHistoryStatsBinsEntry counter
              when the mefSoamDmCfgMeasBinType is 'backwardFrameDelay'.
          bFrameDelayBackwardMin(11)
              Enables/disables the mefSoamDmCurrentStatsFrameDelayBackwardMin
              and mefSoamDmHistoryStatsFrameDelayBackwardMin counters.
          bFrameDelayBackwardMax(12)
              Enables/disables the mefSoamDmCurrentStatsFrameDelayBackwardMax
              and mefSoamDmHistoryStatsFrameDelayBackwardMax counters.
          bFrameDelayBackwardAvg(13)
              Enables/disables the mefSoamDmCurrentStatsFrameDelayBackwardAvg
              and mefSoamDmHistoryStatsFrameDelayBackwardAvg counters.
          bIfdvForwardBins(14)
              Enables/disables the mefSoamDmCurrentStatsBinsEntry counter
              and the mefSoamDmHistoryStatsBinsEntry counter
              when the mefSoamDmCfgMeasBinType is 'forwardIfdv'.
          bIfdvForwardMin(15)
              Enables/disables the mefSoamDmCurrentStatsIfdvForwardMin
              and mefSoamDmHistoryStatsIfdvForwardMin counters.
          bIfdvForwardMax(16)
              Enables/disables the mefSoamDmCurrentStatsIfdvForwardMax
              and mefSoamDmHistoryStatsIfdvForwardMax counters.
          bIfdvForwardAvg(17)
              Enables/disables the mefSoamDmCurrentStatsIfdvForwardAvg
              and mefSoamDmHistoryStatsIfdvForwardAvg counters.
          bIfdvBackwardBins(18)
              Enables/disables the mefSoamDmCurrentStatsBinsEntry counter
              and the mefSoamDmHistoryStatsBinsEntry counter
              when the mefSoamDmCfgMeasBinType is 'backwardIfdv'.
          bIfdvBackwardMin(19)
              Enables/disables the mefSoamDmCurrentStatsIfdvBackwardMin
              and mefSoamDmHistoryStatsIfdvBackwardMin counters.
          bIfdvBackwardMax(20)
              Enables/disables the mefSoamDmCurrentStatsIfdvBackwardMax
              and mefSoamDmHistoryStatsIfdvBackwardMax counters.
          bIfdvBackwardAvg(21)
              Enables/disables the mefSoamDmCurrentStatsIfdvBackwardAvg
              and mefSoamDmHistoryStatsIfdvBackwardAvg counters.
          bIfdvTwoWayBins(22)
              Enables/disables the mefSoamDmCurrentStatsBinsEntry counter
              and the mefSoamDmHistoryStatsBinsEntry counter
              when the mefSoamDmCfgMeasBinType is 'twoWayIfdv'.
          bIfdvTwoWayMin(23)
              Enables/disables the mefSoamDmCurrentStatsIfdvTwoWayMin
              and mefSoamDmHistoryStatsIfdvTwoWayMin counters.
          bIfdvTwoWayMax(24)
              Enables/disables the mefSoamDmCurrentStatsIfdvTwoWayMax
              and mefSoamDmHistoryStatsIfdvTwoWayMax counters.
          bIfdvTwoWayAvg(25)
              Enables/disables the mefSoamDmCurrentStatsIfdvTwoWayAvg
              and mefSoamDmHistoryStatsIfdvTwoWayAvg counters.
          bFrameDelayRangeForwardBins(26)
              Enables/disables the mefSoamDmCurrentStatsBinsEntry counter
              and the mefSoamDmHistoryStatsBinsEntry counter
              when the mefSoamDmCfgMeasBinType is 'forwardFrameDelayRange'.
          bFrameDelayRangeForwardMax(27)
              Enables/disables the mefSoamDmCurrentStatsFrameDelayRangeForwardMax
              and mefSoamDmHistoryStatsFrameDelayRangeForwardMax counters.
          bFrameDelayRangeForwardAvg(28)
              Enables/disables the mefSoamDmCurrentStatsFrameDelayRangeForwardAvg
              and mefSoamDmHistoryStatsFrameDelayRangeForwardAvg counters.
          bFrameDelayRangeBackwardBins(29)
              Enables/disables the mefSoamDmCurrentStatsBinsEntry counter
              and the mefSoamDmHistoryStatsBinsEntry counter
              when the mefSoamDmCfgMeasBinType is 'backwardFrameDelayRange'.
          bFrameDelayRangeBackwardMax(30)
              Enables/disables the mefSoamDmCurrentStatsFrameDelayRangeBackwardMax
              and mefSoamDmHistoryStatsFrameDelayRangeBackwardMax counters.
          bFrameDelayRangeBackwardAvg(31)
              Enables/disables the mefSoamDmCurrentStatsFrameDelayRangeBackwardAvg
              and mefSoamDmHistoryStatsFrameDelayRangeBackwardAvg counters.
          bFrameDelayRangeTwoWayBins(32)
              Enables/disables the mefSoamDmCurrentStatsBinsEntry counter
              and the mefSoamDmHistoryStatsBinsEntry counter
              when the mefSoamDmCfgMeasBinType is 'twoWayFrameDelayRange'.
          bFrameDelayRangeTwoWayMax(33)
              Enables/disables the mefSoamDmCurrentStatsFrameDelayRangeTwoWayMax
              and mefSoamDmHistoryStatsFrameDelayRangeTwoWayMax counters.
          bFrameDelayRangeTwoWayAvg(34)
              Enables/disables the mefSoamDmCurrentStatsFrameDelayRangeTwoWayAvg
              and mefSoamDmHistoryStatsFrameDelayRangeTwoWayAvg counters.
          bMeasuredStatsFrameDelayTwoWay(35)
              Enables/disables the mefSoamDmMeasuredStatsFrameDelayTwoWay
              counter.
          bMeasuredStatsFrameDelayForward(36)
              Enables/disables the mefSoamDmMeasuredStatsFrameDelayForward
              counter.
          bMeasuredStatsFrameDelayBackward(37)
              Enables/disables the mefSoamDmMeasuredStatsFrameDelayBackward
              counter.
          bMeasuredStatsIfdvTwoWay(38)
              Enables/disables the mefSoamDmMeasuredStatsIfdvTwoWay
              counter.
          bMeasuredStatsIfdvForward(39)
              Enables/disables the mefSoamDmMeasuredStatsIfdvForward
              counter.
          bMeasuredStatsIfdvBackward(40)
              Enables/disables the mefSoamDmMeasuredStatsIfdvBackward
              counter.";
        reference   
         "[MEF SOAM-PM]";
      }

      leaf mefSoamDmCfgMessagePeriod {
        type mef-soam:MefSoamTcMeasurementPeriodType;
        units "ms";
        config true;
        description 
         "This object specifies the interval between Delay Measurement 
          OAM message transmission. For Delay Measurement monitoring 
          applications, the default value is 100ms.
          
          This object can only be written at row creation time and cannot be 
          modified once it has been created.";
        reference   
         "[MEF SOAM-PM] R61, R62, D22, R95, R96, D39";
      }

      leaf mefSoamDmCfgPriority {
        type ieee8021-tc:IEEE8021PriorityValue;
        config true;
        description 
         "This object specifies the priority of frames with 
          Delay Measurement OAM message information.
          
          The default value is to be the value which yields the lowest frame 
          loss.
          
          This object can only be written at row creation time and cannot be 
          modified once it has been created.";
        reference   
         "[MEF SOAM-PM] R1, R2, R56, D21, R57, R58, R90-R94, D28;
          [MEF 10.2.1] Section 6.8";
      }

      leaf mefSoamDmCfgFrameSize {
        type uint32;
        config true;
        description 
         "This object specifies the Delay Measurement frame size between
          64 bytes and the maximum transmission unit of the EVC. 
          
          The range of frame sizes from 64 through 2000 octets need to be
          supported, and the range of frame sizes from 2001 through 9600 octets
          is suggested to be supported.  
          
          The adjustment to the frame size of the standard frame size is 
          accomplished by the addition of a Data or Test TLV. A Data or Test TLV
          is only added to the frame if the frame size is greater than 64 bytes.
          
          This object is only valid for the entity transmitting the Delay
          Measurement frames (dmDmm, dm1DmTx) and is ignored by the entity 
          receiving frames.
          
          In addition, this object is not valid when mefSoamDmCfgVersion is 0.
          
          This object can only be written at row creation time and cannot be 
          modified once it has been created.";
        reference   
         "[MEF SOAM-PM] R63, R64, D23, D24, R97, R98, D40, D41";
      }

      leaf mefSoamDmCfgDataPattern {
        type mef-soam:MefSoamTcDataPatternType;
        config true;
        description 
         "This object specifies the DM data pattern included in a Data TLV
          when the size of the DM frame is determined by the 
          mefSoamDmFrameSize object and mefSoamDmTestTlvIncluded is 'false'.
          If the frame size object does not define the DM frame size or 
          mefSoamDmTestTlvIncluded is 'true' the value of this object is 
          ignored.
          
          This object can only be written at row creation time and cannot be 
          modified once it has been created.";
      }

      leaf mefSoamDmCfgTestTlvIncluded {
        type smiv2:TruthValue;
        config true;
        description 
         "Indicates whether a Test TLV or Data TLV is included when the size
          of the DM frame is determined by the mefSoamDmFrameSize object.
          A value of 'true' indicates that the Test TLV is to be included. A 
          value of 'false' indicates that the Data TLV is to be included.
          
          If the frame size object does not define the DM frame size
          the value of this object is ignored.
          
          This object can only be written at row creation time and cannot be 
          modified once it has been created.";
        reference   
         "[Y.1731] 9.3";
      }

      leaf mefSoamDmCfgTestTlvPattern {
        type mef-soam:MefSoamTcTestPatternType;
        config true;
        description 
         "This object specifies the type of test pattern to be
          sent in the DM frame Test TLV when the size
          of DM PDU is determined by the mefSoamDmFrameSize object and 
          mefSoamDmTestTlvIncluded is 'true'. If the frame size object
          does not define the DM frame size or mefSoamDmTestTlvIncluded
          is 'false' the value of this object is ignored. 
          
          This object can only be written at row creation time and cannot be 
          modified once it has been created.";
      }

      leaf mefSoamDmCfgMeasurementInterval {
        type uint32 {
          range "1..1440";
        }
        units "minutes";
        config true;
        description 
         "This object specifies a Measurement Interval in minutes.
          
          A Measurement Interval 15 minutes needs to be supported, other intervals
          may be supported.
          
          This object can only be written at row creation time and cannot be 
          modified once it has been created.";
        reference   
         "[MEF SOAM-PM] R16, R17";
      }

      leaf mefSoamDmCfgNumIntervalsStored {
        type uint32 {
          range "2..1000";
        }
        config true;
        description 
         "This object specifies the number of completed Measurement Intervals
          to store in the history statistic table.
          
          At least 32 completed Measurement Intervals are to be stored. 96 
          Measurement Intervals are recommended to be stored.
          
          This object can only be written at row creation time and cannot be 
          modified once it has been created.";
        reference   
         "[MEF SOAM-PM] R21, D8, D9";
      }

      leaf mefSoamDmCfgDestMacAddress {
        type yang:mac-address;
        config true;
        description 
         "The Target or Destination MAC Address Field to be transmitted.
          
          If mefSoamDmCfgType is 'dmDmm', the destination address is to be the 
          unicast address of the destination MEP. An error is returned if this 
          object is set to a multicast address.
          
          If mefSoamDmCfgType is 'dm1DmTx', the destination address is normally the
          unicast address of the destination MEP, but can be a multicast address  
          indicating the level of the MEG: 01-80-c2-00-00-3y, where y is the
          level of the MEG.  An error is returned if this object is set to any
          other multicast address.
          
          If mefSoamDmCfgType is 'dm1DmRx', this object is ignored.
          
          This address will be used if the value of the object
          mefSoamDmDestIsMepId is 'false'. 
          
          This object is only valid for the entity transmitting the 
          SOAM DM frames and is ignored by the entity receiving 
          SOAM DM frames.
          
          This object can only be written at row creation time and cannot be 
          modified once it has been created.";
        reference   
         "[MEF SOAM-PM] R55, R89";
      }

      leaf mefSoamDmCfgDestMepId {
        type ieee8021-cfm:Dot1agCfmMepIdOrZero;
        config true;
        description 
         "The Maintenance Association End Point Identifier of
          another MEP in the same Maintenance Association to which
          the SOAM DM frame is to be sent.
          
          This address will be used if the value of the column
          mefSoamDmDestIsMepId is 'true'. A value of zero
          means that the destination MEP ID has not been configured.
          
          This object is only valid for the entity transmitting the Delay
          Measurement frames, types 'dmDmm' and 'dm1DmTx'. It is not applicable
          for the 'dm1DmRx' type.
          
          This object can only be written at row creation time and cannot be 
          modified once it has been created.";
        reference   
         "[MEF SOAM-PM] R55, R89";
      }

      leaf mefSoamDmCfgDestIsMepId {
        type smiv2:TruthValue;
        config true;
        description 
         "A value of 'true' indicates that MEPID of the target MEP is used for
          SOAM DM frame transmission.
          
          A value of 'false' indicates that the destination MAC address of the
          target MEP is used for SOAM DM frame transmission.
          
          This object is only valid for the entity transmitting the Delay
          Measurement frames, types 'dmDmm' and 'dm1DmTx'. It is not applicable
          for the 'dm1DmRx type.
          
          This object can only be written at row creation time and cannot be 
          modified once it has been created.";
        reference   
         "[MEF SOAM-PM] R55, R89";
      }

      leaf mefSoamDmCfgSourceMacAddress {
        type yang:mac-address;
        config true;
        description 
         "The Source MAC Address Field of the received SOAM DM session PDUs.
          
          If mefSoamDmCfgType is dm1DmRx this object indicates the source
          address of the dm1DmTx DM session. 
          
          This object is only valid for mefSoamDmCfgType set to dm1DmRx. It is
          ignored for mefSoamDmCfgType set to dmDmm or dm1DmTx.
          
          This object can only be written at row creation time and cannot be 
          modified once it has been created.";
        reference   
         "[MEF SOAM-PM] R55, R89";
      }

      leaf mefSoamDmCfgStartTimeType {
        type mef-soam:MefSoamTcOperationTimeType;
        config true;
        description 
         "This object specifies the type of start time of the SOAM DM
          session. The start time can be disabled (none), immediate, relative,
          or fixed.
          
          The value of 'none' is illegal and a write error will be returned
          if this value is used.
          
          The value of 'immediate' starts the SOAM DM session when the 
          mefSoamDmCfgEnabled is true.
          
          The value of 'fixed' starts the SOAM DM session when the 
          mefSoamDmFixedStartDateAndTime is less than or equal to the current
          system date and time and mefSoamDmCfgEnabled is true. This value is used
          to implement an On-Demand fixed time PM session. 
          
          The value of 'relative' starts the SOAM DM session when the current
          system date and time minus the mefSoamDmRelativeStartTime is greater than
          or equal to the system date and time when the mefSoamDmStartTimeType
          object was written and mefSoamDmCfgEnabled is true. This value is used
          to implement an On-Demand relative time PM session.
          
          This object can only be written at row creation time and cannot be 
          modified once it has been created.";
        reference   
         "[MEF SOAM-PM] R3, R7, R8, D1";
      }

      leaf mefSoamDmCfgFixedStartDateAndTime {
        type smiv2:DateAndTime;
        config true;
        description 
         "This object specifies the fixed start date/time for the 
          SOAM Delay Measurement session. This object is used only used if 
          mefSoamDmStartTimeType is 'fixed' and is ignored otherwise.
          
          The default value is year 0000, month 01, day 01, time 00:00:00.00.
          
          This object can only be written at row creation time and cannot be 
          modified once it has been created.";
        reference   
         "[MEF SOAM-PM] R9";
      }

      leaf mefSoamDmCfgRelativeStartTime {
        type smiv2:TimeInterval;
        config true;
        description 
         "This object specifies the relative start time, from 
          the current system time, for the SOAM DM session. This
          object is used only if mefSoamDmStartTimeType is 'relative' 
          and is ignored otherwise.
          
          This object can only be written at row creation time and cannot be 
          modified once it has been created.";
        reference   
         "[MEF SOAM-PM] R9";
      }

      leaf mefSoamDmCfgStopTimeType {
        type mef-soam:MefSoamTcOperationTimeType;
        config true;
        description 
         "This object specifies the type of stop time to terminate the
          SOAM DM session. The stop time can be forever (none), relative, or 
          fixed.
          
          The value of 'none' indicates that the SOAM DM session never ends once it
          has started unless the session is disabled.
          
          The value of 'immediate' is illegal and a write error will be returned
          if this value is used.
          
          The value of 'fixed' stops the SOAM DM session when the 
          mefSoamDmFixedStopDateAndTime is less than or equal
          to the current system date. This
          value is used to implement an On-Demand fixed time PM session.
          
          The value of 'relative' stops the SOAM DM session when the time 
          indicated by mefSoamDmRelativeStopTime has passed since the session
          start time as determined by the mefSoamDmCfgStartTimeType, 
          mefSoamDmCfgFixedStartDateAndTime and mefSoamDmCfgRelativeStartTime
          objects.
          This value is used to implement an On-Demand relative time PM session.
          
          This object can only be written at row creation time and cannot be 
          modified once it has been created.";
        reference   
         "[MEF SOAM-PM] R3, R10, D2";
      }

      leaf mefSoamDmCfgFixedStopDateAndTime {
        type smiv2:DateAndTime;
        config true;
        description 
         "This object specifies the fixed stop date/time for the 
          SOAM Delay Measurement session. This object is used only used 
          if mefSoamDmStopTimeType is 'fixed' and is ignored otherwise.
          
          The default value is year 0000, month 01, day 01, time 00:00:00.00.
          
          This object can only be written at row creation time and cannot be 
          modified once it has been created.";
        reference   
         "[MEF SOAM-PM] R10, R13";
      }

      leaf mefSoamDmCfgRelativeStopTime {
        type smiv2:TimeInterval;
        config true;
        description 
         "This object specifies the relative stop time, from the
          session start time, to stop the SOAM DM session.  This
          object is used only if mefSoamDmStopTimeType is 'relative' and is 
          ignored otherwise.
          
          This object can only be written at row creation time and cannot be 
          modified once it has been created.";
        reference   
         "[MEF SOAM-PM] R11";
      }

      leaf mefSoamDmCfgRepetitionTime {
        type uint32 {
          range "0..31536000";
        }
        units "seconds";
        config true;
        description 
         "This object specifies a configurable repetition time between
          Measurement Intervals in a Delay Measurement session in seconds. 
          
          If the value is 0 (none), there is no time gap between the end of one
          Measurement Interval and the start of a new Measurement Interval.
          This is the normal usage case.
          
          If the value is greater than one Measurement Interval there is time gap
          between the end of one Measurement Interval and the start of the next
          Measurement Interval.  The repetition time specifies the time between
          the start of consecutive Measurement Intervals; hence the gap between
          the end of one Measurement Interval and the start of the next is equal
          to the difference between the repetition time and the measurement
          interval.  During this gap, no SOAM PDUs are sent for this session and
          no measurements are made.
          
          If the value is greater 0 but less than or equal to the measurement
          interval, an error is returned.
          
          This object can only be written at row creation time and cannot be 
          modified once it has been created.";
        reference   
         "[MEF SOAM-PM] R18, D3, R19, R20";
      }

      leaf mefSoamDmCfgAlignMeasurementIntervals {
        type smiv2:TruthValue;
        config true;
        description 
         "This object specifies whether the Measurement Intervals for
          the Delay Measurement session are aligned with a zero offset to
          real time.
          
          The value 'true' indicates that each Measurement Interval starts
          at a time which is aligned to NE time source hour, if the repetition
          time (or the Measurement Interval, if the repetition time is 0) is
          a factor of an hour, i.e. 60min/15min = 4. For instance, a
          Measurement Interval/Repetition Time of 15 minutes would stop/start 
          the Measurement Interval at 0, 15, 30, and 45 minutes of an hour. A 
          Measurement Interval/Repetition Time of 7 minutes would not align
          to the hour since 7 minutes is NOT a factor of an hour, i.e.
          60min/7min = 8.6.  In this case the behavior is the same as if the
          object is set to 'false'.
          
          The value 'false' indicates that the first Measurement Interval starts
          at an arbitrary time and each subsequent Measurement Interval starts
          at a time which is determined by mefSoamLmCfgRepetitionTime.
          
          This object can only be written at row creation time and cannot be 
          modified once it has been created.";
        reference   
         "[MEF SOAM-PM] D4, D5, D6";
      }

      leaf mefSoamDmCfgAlignMeasurementOffset {
        type uint32 {
          range "0..525600";
        }
        units "minutes";
        config true;
        description 
         "This object specifies the offset in minutes from the time of day value 
          if mefSoamDmCfgAlignMeasurementIntervals is 'true' and the repetition 
          time is a factor of 60 minutes. If not, the value of this object
          is ignored.
          
          If the Measurement Interval is 15 minutes and 
          mefSoamDmCfgAlignMeasurementIntervals is true and if this object was
          set to 5 minutes, the Measurement Intervals would start at 5, 20, 35, 50
          minutes past each hour.
          
          This object can only be written at row creation time and cannot be 
          modified once it has been created.";
        reference   
         "[MEF SOAM-PM] D7";
      }

      leaf mefSoamDmCfgNumMeasBinsPerFrameDelayInterval {
        type uint32 {
          range "2..100";
        }
        config true;
        description 
         "This object specifies the number of measurement bins 
          per Measurement Interval for Frame Delay measurements. 
          
          At least 3 bins are to be supported; at least 10 bins are recommended
          to be supported.
          
          This object can only be written at row creation time and cannot be 
          modified once it has been created.";
        reference   
         "[MEF SOAM-PM] R27, D11, R28, D12";
      }

      leaf mefSoamDmCfgNumMeasBinsPerInterFrameDelayVariationInterval {
        type uint32 {
          range "2..100";
        }
        config true;
        description 
         "This object specifies the number of measurement bins 
          per Measurement Interval for Inter-Frame Delay Variation 
          measurements. 
          
          The minimum number of measurement bins to be supported is 2. The 
          desired number of measurements bins to be supported is 10.
          
          This object can only be written at row creation time and cannot be 
          modified once it has been created.";
        reference   
         "[MEF SOAM-PM] R29, D13, R30, D14";
      }

      leaf mefSoamDmCfgInterFrameDelayVariationSelectionOffset {
        type uint32 {
          range "1..100";
        }
        config true;
        description 
         "This object specifies the selection offset for 
          Inter-Frame Delay Variation measurements.  If this value 
          is set to n, then the IFDV is calculated by taking the 
          difference in frame delay between frame F and frame (F+n).
          
          This object can only be written at row creation time and cannot be 
          modified once it has been created.";
        reference   
         "[MEF SOAM-PM] O4, D25, O6, D42";
      }

      leaf mefSoamDmCfgNumMeasBinsPerFrameDelayRangeInterval {
        type uint32 {
          range "2..100";
        }
        config true;
        description 
         "This object specifies the number of measurement bins 
          per Measurement Interval for Frame Delay Range measurements. 
          
          At least 2 bins are to be supported; at least 10 bins are recommended
          to be supported.
          
          This object can only be written at row creation time and cannot be 
          modified once it has been created.";
        reference   
         "[MEF SOAM-PM] R31, D15, R32, D16";
      }

      leaf mefSoamDmCfgSessionType {
        type mef-soam:MefSoamTcSessionType;
        config true;
        description 
         "This object indicates whether the current session is defined to
          be 'Proactive' or 'On-Demand'. A value of 'proactive'
          indicates the current session is 'Proactive'. A value of 'onDemand'
          indicates the current session is 'On-Demand'. 
          
          This object can only be written at row creation time and cannot be 
          modified once it has been created.";
        reference   
         "[MEF SOAM-PM] R3";
      }

      leaf mefSoamDmCfgSessionStatus {
        type mef-soam:MefSoamTcStatusType;
        description 
         "This object indicates the current status of the DM session. A value
          of 'active' indicates the current DM session is active, i.e. the current
          time lies between the start time and the stop time, and 
          mefSoamDmCfgEnabled is true. A value of 'notActive' indicates the
          current DM session is not active, i.e. it has not started yet, has 
          stopped upon reaching the stop time, or is disabled.";
      }

      leaf mefSoamDmCfgHistoryClear {
        type smiv2:TruthValue;
        config true;
        description 
         "This object when written clears the Delay Measurement history
          tables (mefSoamDmHistoryStatsTable and mefSoamDmHistoryStatsBinsTable)
          - all rows are deleted.  When read the value always returns 'false'. 
          
          Writing this value does not change the current stat table,
          nor any of the items in the configuration table.
          
          Writing this object at row creation has no effect.";
      }

      leaf mefSoamDmCfgRowStatus {
        type smiv2:RowStatus;
        config true;
        description 
         "The status of the row.
          
          The writable columns in a row cannot be changed if the row
          is active, except for mefSoamDmCfgEnabled and mefSoamDmCfgHistoryClear
          objects. All columns are to have a valid value before a row
          can be activated.";
      }
    }


    /* XXX table comments here XXX */

    list mefSoamDmCfgMeasBinEntry {

      key "dot1agCfmMdIndex dot1agCfmMaIndex 
           dot1agCfmMepIdentifier mefSoamDmCfgIndex 
           mefSoamDmCfgMeasBinType mefSoamDmCfgMeasBinNumber";
      description   
       "The conceptual row of mefSoamDmCfgMeasBinTable.";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamDmCfgIndex {
        type leafref {
          path "/mef-soam-pm:mefSoamPmDmObjects/mef-soam-pm:mefSoamDmCfgEntry/mef-soam-pm:mefSoamDmCfgIndex";
        }
        config true;
        description 
         "Automagically generated leafref leaf.";
      }

      leaf mefSoamDmCfgMeasBinType {
        type mef-soam:MefSoamTcDelayMeasurementBinType;
        description 
         "This object specifies whether the bin number is for 
          Frame Delay or Inter-Frame Delay Variation.";
      }

      leaf mefSoamDmCfgMeasBinNumber {
        type uint32;
        description 
         "This object specifies the bin number for the 
          configured boundary.  The first bin has bin number 1.";
      }

      leaf mefSoamDmCfgMeasBinLowerBound {
        type uint32;
        units "microseconds (us)";
        config true;
        description 
         "This object specifies the lower boundary for a 
          measurement bin. The upper boundary is defined by the next bin
          value or infinite for the last bin defined.
          The measurement boundary for each measurement bin is to  
          be larger than the measurement boundary of the preceding 
          measurement bin. By default, the next bin is set to 5000us larger 
          than the lower bin boundary. 
          
          The values in a bin boundary object represents the time range 
          used to segregate delay data into the appropriate statistical
          data bin. For five bins with default values, each bin has the 
          following time range:
          
          bin 1 =     0, range is 0us <= measurement < 5,000us
          bin 2 =  5000, range is 5,000us <= measurement < 10,000us
          bin 3 = 10000, range is 10,000us <= measurement < 15,000us
          bin 4 = 15000, range is 15,000us <= measurement < 20,000us
          bin 5 = 20000, range is 20,000us <= measurement < infinity
          
          The first bin boundary (mefSoamDmCfgBinNumber set to 1) always contains 
          the value of 0. Attempting to write a non-zero value to this bin will 
          result in an error.";
        reference   
         "[MEF SOAM-PM] R33, R35, D17";
      }
    }


    /* XXX table comments here XXX */

    list mefSoamDmMeasuredStatsEntry {

      key "dot1agCfmMdIndex dot1agCfmMaIndex 
           dot1agCfmMepIdentifier mefSoamDmCfgIndex";
      description   
       "The conceptual row of mefSoamDmMeasuredStatsTable";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamDmCfgIndex {
        type leafref {
          path "/mef-soam-pm:mefSoamPmDmObjects/mef-soam-pm:mefSoamDmCfgEntry/mef-soam-pm:mefSoamDmCfgIndex";
        }
        config true;
        description 
         "Automagically generated leafref leaf.";
      }

      leaf mefSoamDmMeasuredStatsFrameDelayTwoWay {
        type uint32;
        units "microseconds";
        description 
         "This object contains the two-way frame delay calculated by this 
          MEP from the last received SOAM PDU.
          
          This object is undefined is mefSoamDmCfgType is dm1DmTx or dm1DmRx.";
        reference   
         "[MEF SOAM-PM] R66";
      }

      leaf mefSoamDmMeasuredStatsFrameDelayForward {
        type uint32;
        units "microseconds";
        description 
         "This object contains the frame delay in the forward direction 
          calculated by this MEP from the last received SOAM PDU. The value of this
          object may not be accurate in the absence of sufficiently precise clock
          synchronization.
          
          This object is undefined is mefSoamDmCfgType is dm1DmTx.";
        reference   
         "[MEF SOAM-PM] R66";
      }

      leaf mefSoamDmMeasuredStatsFrameDelayBackward {
        type uint32;
        units "microseconds";
        description 
         "This object contains the frame delay in the backward direction 
          calculated by this MEP from the last received SOAM PDU. The value of this
          object may not be accurate in the absence of sufficiently precise clock
          synchronization.
          
          This object is undefined is mefSoamDmCfgType is dm1DmTx or dm1DmRx.";
        reference   
         "[MEF SOAM-PM] R66";
      }

      leaf mefSoamDmMeasuredStatsIfdvTwoWay {
        type uint32;
        units "microseconds";
        description 
         "This object contains the last two-way inter-frame delay
          interval calculated by this MEP.
          
          The value of this object is undefined when mefSoamDmCfgType
          is dm1DmTx or dm1DmRx.";
        reference   
         "[MEF SOAM-PM] R66";
      }

      leaf mefSoamDmMeasuredStatsIfdvForward {
        type uint32;
        units "microseconds";
        description 
         "This object contains the last one-way inter-frame delay
          interval in the forward direction calculated by this MEP.
          
          The value of this object is undefined when mefSoamDmCfgType
          is dm1DmTx.";
        reference   
         "[MEF SOAM-PM] R66";
      }

      leaf mefSoamDmMeasuredStatsIfdvBackward {
        type uint32;
        units "microseconds";
        description 
         "This object contains the last one-way inter-frame delay
          interval in the backward direction calculated by this MEP.
          
          The value of this object is undefined when mefSoamDmCfgType
          is dm1DmTx or dm1DmRx.";
        reference   
         "[MEF SOAM-PM] R66";
      }
    }


    /* XXX table comments here XXX */

    list mefSoamDmCurrentStatsEntry {

      key "dot1agCfmMdIndex dot1agCfmMaIndex 
           dot1agCfmMepIdentifier mefSoamDmCfgIndex";
      description   
       "The conceptual row of mefSoamDmCurrentStatsTable";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamDmCfgIndex {
        type leafref {
          path "/mef-soam-pm:mefSoamPmDmObjects/mef-soam-pm:mefSoamDmCfgEntry/mef-soam-pm:mefSoamDmCfgIndex";
        }
        config true;
        description 
         "Automagically generated leafref leaf.";
      }

      leaf mefSoamDmCurrentStatsIndex {
        type uint32;
        description 
         "The index for the current Measurement Interval for this
          PM session.  This value will become the value for
          mefSoamDmHistoryStatsIndex once the Measurement Interval
          is completed.
          
          Measurement Interval indexes are assigned sequentially by
          the SNMP Agent.  The first Measurement Interval that occurs after
          the session is started is assigned index 1.";
      }

      leaf mefSoamDmCurrentStatsStartTime {
        type smiv2:DateAndTime;
        description 
         "The time that the current Measurement Interval started.";
        reference   
         "[MEF SOAM-PM] R22, R66, R100";
      }

      leaf mefSoamDmCurrentStatsElapsedTime {
        type smiv2:TimeInterval;
        description 
         "The time that the current Measurement Interval has been running, in 0.01
          seconds.";
        reference   
         "[MEF SOAM-PM] R24, R66, R100";
      }

      leaf mefSoamDmCurrentStatsSuspect {
        type smiv2:TruthValue;
        description 
         "Whether the Measurement Interval has been marked as suspect.
          
          The object is to be set to false at the start of a measurement
          interval. It is set to true when there is a discontinuity in the 
          performance measurements during the Measurement Interval.  Conditions
          for a discontinuity include, but are not limited to the following:
          
          1 - The local time-of-day clock is adjusted by at least 10 seconds
          2 - The conducting of a performance measurement is halted before the
              current Measurement Interval is completed
          3 - A local test, failure, or reconfiguration that disrupts service";
        reference   
         "[MEF SOAM-PM] R39, R40, R41";
      }

      leaf mefSoamDmCurrentStatsFrameDelayTwoWayMin {
        type uint32;
        units "microseconds";
        description 
         "This object contains the minimum two-way frame delay
          calculated by this MEP for this Measurement Interval.
          
          This object is undefined is mefSoamDmCfgType is dm1DmTx or dm1DmRx.";
        reference   
         "[MEF SOAM-PM] R66";
      }

      leaf mefSoamDmCurrentStatsFrameDelayTwoWayMax {
        type uint32;
        units "microseconds";
        description 
         "This object contains the maximum two-way frame delay
          calculated by this MEP for this Measurement Interval.
          
          This object is undefined is mefSoamDmCfgType is dm1DmTx or dm1DmRx.";
        reference   
         "[MEF SOAM-PM] R66";
      }

      leaf mefSoamDmCurrentStatsFrameDelayTwoWayAvg {
        type uint32;
        units "microseconds";
        description 
         "This object contains the average two-way frame delay
          calculated by this MEP for this Measurement Interval.
          
          This object is undefined is mefSoamDmCfgType is dm1DmTx or dm1DmRx.";
        reference   
         "[MEF SOAM-PM] R66";
      }

      leaf mefSoamDmCurrentStatsFrameDelayForwardMin {
        type uint32;
        units "microseconds";
        description 
         "This object contains the minimum one-way frame delay
          in the forward direction calculated by this MEP for this
          Measurement Interval. The value of this object may not be accurate
          in the absence of sufficiently precise clock synchronization.
          
          This object is undefined is mefSoamDmCfgType is dm1DmTx.";
        reference   
         "[MEF SOAM-PM] R67, R101";
      }

      leaf mefSoamDmCurrentStatsFrameDelayForwardMax {
        type uint32;
        units "microseconds";
        description 
         "This object contains the maximum one-way frame delay
          in the forward direction calculated by this MEP for this
          Measurement Interval. The value of this object may not be accurate
          in the absence of sufficiently precise clock synchronization.
          
          This object is undefined is mefSoamDmCfgType is dm1DmTx.";
        reference   
         "[MEF SOAM-PM] R67, R101";
      }

      leaf mefSoamDmCurrentStatsFrameDelayForwardAvg {
        type uint32;
        units "microseconds";
        description 
         "This object contains the average one-way frame delay
          in the forward direction calculated by this MEP for this
          Measurement Interval. The value of this object may not be accurate
          in the absence of sufficiently precise clock synchronization.
          
          This object is undefined is mefSoamDmCfgType is dm1DmTx.";
        reference   
         "[MEF SOAM-PM] R67, R101";
      }

      leaf mefSoamDmCurrentStatsFrameDelayBackwardMin {
        type uint32;
        units "microseconds";
        description 
         "This object contains the minimum one-way frame delay
          in the backward direction calculated by this MEP for this
          Measurement Interval. The value of this object may not be accurate
          in the absence of sufficiently precise clock synchronization.
          
          This object is undefined is mefSoamDmCfgType is dm1DmTx or dm1DmRx.";
        reference   
         "[MEF SOAM-PM] R67";
      }

      leaf mefSoamDmCurrentStatsFrameDelayBackwardMax {
        type uint32;
        units "microseconds";
        description 
         "This object contains the maximum one-way frame delay
          in the backward direction calculated by this MEP for this
          Measurement Interval. The value of this object may not be accurate
          in the absence of sufficiently precise clock synchronization.
          
          This object is undefined is mefSoamDmCfgType is dm1DmTx or dm1DmRx.";
        reference   
         "[MEF SOAM-PM] R67";
      }

      leaf mefSoamDmCurrentStatsFrameDelayBackwardAvg {
        type uint32;
        units "microseconds";
        description 
         "This object contains the average one-way frame delay
          in the backward direction calculated by this MEP for this
          Measurement Interval. The value of this object may not be accurate
          in the absence of sufficiently precise clock synchronization.
          
          This object is undefined is mefSoamDmCfgType is dm1DmTx or dm1DmRx.";
        reference   
         "[MEF SOAM-PM] R67";
      }

      leaf mefSoamDmCurrentStatsIfdvForwardMin {
        type uint32;
        units "microseconds";
        description 
         "This object contains the minimum one-way inter-frame delay
          interval in the forward direction calculated by this MEP for this
          Measurement Interval. 
          
          The value of this object is undefined when mefSoamDmCfgType
          is dm1DmTx.";
        reference   
         "[MEF SOAM-PM] R66, R100";
      }

      leaf mefSoamDmCurrentStatsIfdvForwardMax {
        type uint32;
        units "microseconds";
        description 
         "This object contains the maximum one-way inter-frame delay
          interval in the forward direction calculated by this MEP for this
          Measurement Interval. 
          
          The value of this object is undefined when mefSoamDmCfgType
          is dm1DmTx.";
        reference   
         "[MEF SOAM-PM] R66, R100";
      }

      leaf mefSoamDmCurrentStatsIfdvForwardAvg {
        type uint32;
        units "microseconds";
        description 
         "This object contains the average one-way inter-frame delay
          interval in the forward direction calculated by this MEP for this
          Measurement Interval. 
          
          The value of this object is undefined when mefSoamDmCfgType
          is dm1DmTx.";
        reference   
         "[MEF SOAM-PM] R66, R100";
      }

      leaf mefSoamDmCurrentStatsIfdvBackwardMin {
        type uint32;
        units "microseconds";
        description 
         "This object contains the minimum one-way inter-frame delay
          interval in the backward direction calculated by this MEP for this
          Measurement Interval. 
          
          The value of this object is undefined when mefSoamDmCfgType
          is dm1DmTx or dm1DmRx.";
        reference   
         "[MEF SOAM-PM] R66";
      }

      leaf mefSoamDmCurrentStatsIfdvBackwardMax {
        type uint32;
        units "microseconds";
        description 
         "This object contains the maximum one-way inter-frame delay
          interval in the backward direction calculated by this MEP for this
          Measurement Interval. 
          
          The value of this object is undefined when mefSoamDmCfgType
          is dm1DmTx or dm1DmRx.";
        reference   
         "[MEF SOAM-PM] R66";
      }

      leaf mefSoamDmCurrentStatsIfdvBackwardAvg {
        type uint32;
        units "microseconds";
        description 
         "This object contains the average one-way inter-frame delay
          interval in the backward direction calculated by this MEP for this
          Measurement Interval. 
          
          The value of this object is undefined when mefSoamDmCfgType
          is dm1DmTx or dm1DmRx.";
        reference   
         "[MEF SOAM-PM] R66";
      }

      leaf mefSoamDmCurrentStatsIfdvTwoWayMin {
        type uint32;
        units "microseconds";
        description 
         "This object contains the minimum two-way inter-frame delay
          interval calculated by this MEP for this
          Measurement Interval. 
          
          The value of this object is undefined when mefSoamDmCfgType
          is dm1DmTx or dm1DmRx.";
      }

      leaf mefSoamDmCurrentStatsIfdvTwoWayMax {
        type uint32;
        units "microseconds";
        description 
         "This object contains the maximum two-way inter-frame delay
          interval calculated by this MEP for this
          Measurement Interval. 
          
          The value of this object is undefined when mefSoamDmCfgType
          is dm1DmTx or dm1DmRx.";
      }

      leaf mefSoamDmCurrentStatsIfdvTwoWayAvg {
        type uint32;
        units "microseconds";
        description 
         "This object contains the average two-way inter-frame delay
          interval calculated by this MEP for this
          Measurement Interval. 
          
          The value of this object is undefined when mefSoamDmCfgType
          is dm1DmTx or dm1DmRx.";
      }

      leaf mefSoamDmCurrentStatsFrameDelayRangeForwardMax {
        type uint32;
        units "microseconds";
        description 
         "This object contains the maximum one-way frame delay range
          in the forward direction calculated by this MEP for this
          Measurement Interval. 
          
          The value of this object is undefined when mefSoamDmCfgType
          is dm1DmTx.";
        reference   
         "[MEF SOAM-PM] R66, R100";
      }

      leaf mefSoamDmCurrentStatsFrameDelayRangeForwardAvg {
        type uint32;
        units "microseconds";
        description 
         "This object contains the average one-way frame delay range
          in the forward direction calculated by this MEP for this
          Measurement Interval. 
          
          The value of this object is undefined when mefSoamDmCfgType
          is dm1DmTx.";
        reference   
         "[MEF SOAM-PM] R66, R100";
      }

      leaf mefSoamDmCurrentStatsFrameDelayRangeBackwardMax {
        type uint32;
        units "microseconds";
        description 
         "This object contains the maximum one-way frame delay range
          in the backward direction calculated by this MEP for this
          Measurement Interval. 
          
          The value of this object is undefined when mefSoamDmCfgType
          is dm1DmTx or dm1DmRx.";
        reference   
         "[MEF SOAM-PM] R66";
      }

      leaf mefSoamDmCurrentStatsFrameDelayRangeBackwardAvg {
        type uint32;
        units "microseconds";
        description 
         "This object contains the average one-way frame delay range
          in the backward direction calculated by this MEP for this
          Measurement Interval. 
          
          The value of this object is undefined when mefSoamDmCfgType
          is dm1DmTx or dm1DmRx.";
        reference   
         "[MEF SOAM-PM] R66";
      }

      leaf mefSoamDmCurrentStatsFrameDelayRangeTwoWayMax {
        type uint32;
        units "microseconds";
        description 
         "This object contains the maximum two-way frame delay range
          calculated by this MEP for this Measurement Interval. 
          
          The value of this object is undefined when mefSoamDmCfgType
          is dm1DmTx or dm1DmRx.";
      }

      leaf mefSoamDmCurrentStatsFrameDelayRangeTwoWayAvg {
        type uint32;
        units "microseconds";
        description 
         "This object contains the average two-way frame delay range
          calculated by this MEP for this Measurement Interval. 
          
          The value of this object is undefined when mefSoamDmCfgType
          is dm1DmTx or dm1DmRx.";
      }

      leaf mefSoamDmCurrentStatsSoamPdusSent {
        type yang:gauge32;
        description 
         "This object contains the count of the number of SOAM PDUs sent
          during this Measurement Interval.
          
          This object applies when mefSoamDmCfgType is dmDmm or dm1DmTx and
          is undefined if mefSoamDmCfgType is dm1DmRx. It indicates the 
          number of DMM or 1DM SOAM frames transmitted.";
        reference   
         "[MEF SOAM-PM] R66, R100";
      }

      leaf mefSoamDmCurrentStatsSoamPdusReceived {
        type yang:gauge32;
        description 
         "This object contains the count of the number of SOAM 
          PDUs received in this Measurement Interval.
          
          This object indicates the number of DMR and 1DM SOAM frames
          received. This object applies when mefSoamDmCfgType is dmDmm or 
          dm1DmRx and is undefined if mefSoamDmCfgType is dm1DmTx.";
        reference   
         "[MEF SOAM-PM] R66, R100";
      }
    }


    /* XXX table comments here XXX */

    list mefSoamDmCurrentStatsBinsEntry {

      key "dot1agCfmMdIndex dot1agCfmMaIndex 
           dot1agCfmMepIdentifier mefSoamDmCfgIndex 
           mefSoamDmCfgMeasBinType mefSoamDmCfgMeasBinNumber";
      description   
       "The conceptual row of mefSoamDmCurrentStatsBinsTable";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamDmCfgIndex {
        type leafref {
          path "/mef-soam-pm:mefSoamPmDmObjects/mef-soam-pm:mefSoamDmCfgEntry/mef-soam-pm:mefSoamDmCfgIndex";
        }
        config true;
        description 
         "Automagically generated leafref leaf.";
      }
      leaf mefSoamDmCfgMeasBinType {
        type mef-soam:MefSoamTcDelayMeasurementBinType;
        description 
         "Automagically generated leafref leaf.";
      }
      leaf mefSoamDmCfgMeasBinNumber {
        type leafref {
          path "/mef-soam-pm:mefSoamPmDmObjects/mef-soam-pm:mefSoamDmCfgMeasBinEntry/mef-soam-pm:mefSoamDmCfgMeasBinNumber";
        }
        description 
         "Automagically generated leafref leaf.";
      }

      leaf mefSoamDmCurrentStatsBinsCounter {
        type yang:gauge32;
        description 
         "This object contains the count of the number of completed
          measurements initiated in this Measurement Interval whose value
          falls within the range specified for this bin (that is, greater
          than or equal to the measurement boundary for the bin, and
          (unless the bin is the last bin) less than the measurement
          boundary for the following bin.
              ";
        reference   
         "[MEF SOAM-PM] R66, R67, R100, R101";
      }
    }


    /* XXX table comments here XXX */

    list mefSoamDmHistoryStatsEntry {

      key "dot1agCfmMdIndex dot1agCfmMaIndex 
           dot1agCfmMepIdentifier mefSoamDmCfgIndex 
           mefSoamDmHistoryStatsIndex";
      description   
       "The conceptual row of mefSoamDmHistoryStatsTable";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamDmCfgIndex {
        type leafref {
          path "/mef-soam-pm:mefSoamPmDmObjects/mef-soam-pm:mefSoamDmCfgEntry/mef-soam-pm:mefSoamDmCfgIndex";
        }
        config true;
        description 
         "Automagically generated leafref leaf.";
      }

      leaf mefSoamDmHistoryStatsIndex {
        type uint32;
        description 
         "The index for the Measurement Interval within this
          PM session.
          
          Measurement Interval indexes are assigned sequentially by
          the SNMP Agent.  The first Measurement Interval that occurs after
          the session is started is assigned index 1.
          
          Referential integrity is necessary, i.e., the index needs to be
          persistent upon a reboot or restart of a device.  The index
          is never reused while this session is active until it wraps to zero.
          The index value keeps increasing up to that time.";
      }

      leaf mefSoamDmHistoryStatsEndTime {
        type smiv2:DateAndTime;
        description 
         "The time that the Measurement Interval ended.";
        reference   
         "[MEF SOAM-PM] R23, R66, R100";
      }

      leaf mefSoamDmHistoryStatsElapsedTime {
        type smiv2:TimeInterval;
        description 
         "The length of time that the Measurement Interval ran for,
          in 0.01 seconds.";
        reference   
         "[MEF SOAM-PM] R66, R100";
      }

      leaf mefSoamDmHistoryStatsSuspect {
        type smiv2:TruthValue;
        description 
         "Whether the Measurement Interval has been marked as suspect.
          
          The object is set to true when there is a discontinuity in the 
          performance measurements during the Measurement Interval.  Conditions
          for a discontinuity include, but are not limited to the following:
          
          1 - The local time-of-day clock is adjusted by at least 10 seconds
          2 - The conducting of a performance measurement is halted before the
              current Measurement Interval is completed
          3 - A local test, failure, or reconfiguration that disrupts service";
        reference   
         "[MEF SOAM-PM] R39, R40, R41, R42";
      }

      leaf mefSoamDmHistoryStatsFrameDelayTwoWayMin {
        type uint32;
        units "microseconds";
        description 
         "This object contains the minimum two-way frame delay
          calculated by this MEP for this Measurement Interval. 
          
          This object is undefined is mefSoamDmCfgType is dm1DmTx or dm1DmRx.";
        reference   
         "[MEF SOAM-PM] R66";
      }

      leaf mefSoamDmHistoryStatsFrameDelayTwoWayMax {
        type uint32;
        units "microseconds";
        description 
         "This object contains the maximum two-way frame delay
          calculated by this MEP for this Measurement Interval. 
          
          This object is undefined is mefSoamDmCfgType is dm1DmTx or dm1DmRx.";
        reference   
         "[MEF SOAM-PM] R66";
      }

      leaf mefSoamDmHistoryStatsFrameDelayTwoWayAvg {
        type uint32;
        units "microseconds";
        description 
         "This object contains the average two-way frame delay
          calculated by this MEP for this Measurement Interval. 
          
          This object is undefined is mefSoamDmCfgType is dm1DmTx or dm1DmRx.";
        reference   
         "[MEF SOAM-PM] R66";
      }

      leaf mefSoamDmHistoryStatsFrameDelayForwardMin {
        type uint32;
        units "microseconds";
        description 
         "This object contains the minimum one-way frame delay
          in the forward direction calculated by this MEP for this
          Measurement Interval. The value of this object may not be accurate
          in the absence of sufficiently precise clock synchronization.
          
          This object is undefined is mefSoamDmCfgType is dm1DmTx.";
        reference   
         "[MEF SOAM-PM] R66, R100";
      }

      leaf mefSoamDmHistoryStatsFrameDelayForwardMax {
        type uint32;
        units "microseconds";
        description 
         "This object contains the maximum one-way frame delay
          in the forward direction calculated by this MEP for this
          Measurement Interval. The value of this object may not be accurate
          in the absence of sufficiently precise clock synchronization.
          
          This object is undefined is mefSoamDmCfgType is dm1DmTx.";
        reference   
         "[MEF SOAM-PM] R66, R100";
      }

      leaf mefSoamDmHistoryStatsFrameDelayForwardAvg {
        type uint32;
        units "microseconds";
        description 
         "This object contains the average one-way frame delay
          in the forward direction calculated by this MEP for this
          Measurement Interval. The value of this object may not be accurate
          in the absence of sufficiently precise clock synchronization.
          
          This object is undefined is mefSoamDmCfgType is dm1DmTx.";
        reference   
         "[MEF SOAM-PM] R66, R100";
      }

      leaf mefSoamDmHistoryStatsFrameDelayBackwardMin {
        type uint32;
        units "microseconds";
        description 
         "This object contains the minimum one-way frame delay
          in the backward direction calculated by this MEP for this
          Measurement Interval. The value of this object may not be accurate
          in the absence of sufficiently precise clock synchronization.
          
          This object is undefined is mefSoamDmCfgType is dm1DmTx or dm1DmRx.";
        reference   
         "[MEF SOAM-PM] R66";
      }

      leaf mefSoamDmHistoryStatsFrameDelayBackwardMax {
        type uint32;
        units "microseconds";
        description 
         "This object contains the maximum one-way frame delay
          in the backward direction calculated by this MEP for this
          Measurement Interval. The value of this object may not be accurate
          in the absence of sufficiently precise clock synchronization.
          
          This object is undefined is mefSoamDmCfgType is dm1DmTx or dm1DmRx.";
        reference   
         "[MEF SOAM-PM] R66";
      }

      leaf mefSoamDmHistoryStatsFrameDelayBackwardAvg {
        type uint32;
        units "microseconds";
        description 
         "This object contains the average one-way frame delay
          in the backward direction calculated by this MEP for this
          Measurement Interval. The value of this object may not be accurate
          in the absence of sufficiently precise clock synchronization.
          
          This object is undefined is mefSoamDmCfgType is dm1DmTx or dm1DmRx.";
        reference   
         "[MEF SOAM-PM] R66";
      }

      leaf mefSoamDmHistoryStatsIfdvForwardMin {
        type uint32;
        units "microseconds";
        description 
         "This object contains the minimum one-way inter-frame delay
          interval in the forward direction calculated by this MEP for this
          Measurement Interval.
          
          The value of this object is undefined when mefSoamDmCfgType
          is dm1DmTx.";
        reference   
         "[MEF SOAM-PM] R66, R100";
      }

      leaf mefSoamDmHistoryStatsIfdvForwardMax {
        type uint32;
        units "microseconds";
        description 
         "This object contains the maximum one-way inter-frame delay
          interval in the forward direction calculated by this MEP for this
          Measurement Interval.
          
          The value of this object is undefined when mefSoamDmCfgType
          is dm1DmTx.";
        reference   
         "[MEF SOAM-PM] R66, R100";
      }

      leaf mefSoamDmHistoryStatsIfdvForwardAvg {
        type uint32;
        units "microseconds";
        description 
         "This object contains the average one-way inter-frame delay
          interval in the forward direction calculated by this MEP for this
          Measurement Interval.
          
          The value of this object is undefined when mefSoamDmCfgType
          is dm1DmTx.";
        reference   
         "[MEF SOAM-PM] R66, R100";
      }

      leaf mefSoamDmHistoryStatsIfdvBackwardMin {
        type uint32;
        units "microseconds";
        description 
         "This object contains the minimum one-way inter-frame delay
          interval in the backward direction calculated by this MEP for this
          Measurement Interval.
          
          The value of this object is undefined when mefSoamDmCfgType
          is dm1DmTx or dm1DmRx.";
        reference   
         "[MEF SOAM-PM] R66";
      }

      leaf mefSoamDmHistoryStatsIfdvBackwardMax {
        type uint32;
        units "microseconds";
        description 
         "This object contains the maximum one-way inter-frame delay
          interval in the backward direction calculated by this MEP for this
          Measurement Interval.
          
          The value of this object is undefined when mefSoamDmCfgType
          is dm1DmTx or dm1DmRx.";
        reference   
         "[MEF SOAM-PM] R66";
      }

      leaf mefSoamDmHistoryStatsIfdvBackwardAvg {
        type uint32;
        units "microseconds";
        description 
         "This object contains the average one-way inter-frame delay
          interval in the backward direction calculated by this MEP for this
          Measurement Interval.
          
          The value of this object is undefined when mefSoamDmCfgType
          is dm1DmTx or dm1DmRx.";
        reference   
         "[MEF SOAM-PM] R66";
      }

      leaf mefSoamDmHistoryStatsIfdvTwoWayMin {
        type uint32;
        units "microseconds";
        description 
         "This object contains the minimum two-way inter-frame delay
          interval calculated by this MEP for this
          Measurement Interval.
          
          The value of this object is undefined when mefSoamDmCfgType
          is dm1DmTx or dm1DmRx.";
      }

      leaf mefSoamDmHistoryStatsIfdvTwoWayMax {
        type uint32;
        units "microseconds";
        description 
         "This object contains the maximum two-way inter-frame delay
          interval calculated by this MEP for this
          Measurement Interval.
          
          The value of this object is undefined when mefSoamDmCfgType
          is dm1DmTx or dm1DmRx.";
      }

      leaf mefSoamDmHistoryStatsIfdvTwoWayAvg {
        type uint32;
        units "microseconds";
        description 
         "This object contains the average two-way inter-frame delay
          interval calculated by this MEP for this
          Measurement Interval.
          
          The value of this object is undefined when mefSoamDmCfgType
          is dm1DmTx or dm1DmRx.";
      }

      leaf mefSoamDmHistoryStatsFrameDelayRangeForwardMax {
        type uint32;
        units "microseconds";
        description 
         "This object contains the maximum one-way Frame Delay Range
          in the forward direction calculated by this MEP for this
          Measurement Interval.
          
          The value of this object is undefined when mefSoamDmCfgType
          is dm1DmTx.";
        reference   
         "[MEF SOAM-PM] R66, R100";
      }

      leaf mefSoamDmHistoryStatsFrameDelayRangeForwardAvg {
        type uint32;
        units "microseconds";
        description 
         "This object contains the average one-way Frame Delay Range
          in the forward direction calculated by this MEP for this
          Measurement Interval.
          
          The value of this object is undefined when mefSoamDmCfgType
          is dm1DmTx.";
        reference   
         "[MEF SOAM-PM] R66, R100";
      }

      leaf mefSoamDmHistoryStatsFrameDelayRangeBackwardMax {
        type uint32;
        units "microseconds";
        description 
         "This object contains the maximum one-way Frame Delay Range
          in the backward direction calculated by this MEP for this
          Measurement Interval.
          
          The value of this object is undefined when mefSoamDmCfgType
          is dm1DmTx or dm1DmRx.";
        reference   
         "[MEF SOAM-PM] R66";
      }

      leaf mefSoamDmHistoryStatsFrameDelayRangeBackwardAvg {
        type uint32;
        units "microseconds";
        description 
         "This object contains the average one-way Frame Delay Range
          in the backward direction calculated by this MEP for this
          Measurement Interval.
          
          The value of this object is undefined when mefSoamDmCfgType
          is dm1DmTx or dm1DmRx.";
        reference   
         "[MEF SOAM-PM] R66";
      }

      leaf mefSoamDmHistoryStatsFrameDelayRangeTwoWayMax {
        type uint32;
        units "microseconds";
        description 
         "This object contains the maximum two-way Frame Delay Range
          calculated by this MEP for this Measurement Interval.
          
          The value of this object is undefined when mefSoamDmCfgType
          is dm1DmTx or dm1DmRx.";
      }

      leaf mefSoamDmHistoryStatsFrameDelayRangeTwoWayAvg {
        type uint32;
        units "microseconds";
        description 
         "This object contains the average two-way Frame Delay Range
          calculated by this MEP for this Measurement Interval.
          
          The value of this object is undefined when mefSoamDmCfgType
          is dm1DmTx or dm1DmRx.";
      }

      leaf mefSoamDmHistoryStatsSoamPdusSent {
        type yang:gauge32;
        description 
         "This object contains the count of the number of SOAM PDUs sent
          during this Measurement Interval.
          
          This object applies when mefSoamDmCfgType is dmDmm or dm1DmTx and
          is undefined if mefSoamDmCfgType is dm1DmRx. It indicates the 
          number of DMM or 1DM SOAM frames transmitted.";
        reference   
         "[MEF SOAM-PM] R66, R100";
      }

      leaf mefSoamDmHistoryStatsSoamPdusReceived {
        type yang:gauge32;
        description 
         "This object contains the count of the number of SOAM 
          PDUs received in this Measurement Interval.
          
          This object indicates the number of DMR and 1DM SOAM frames
          received. This object applies when mefSoamDmCfgType is dmDmm or 
          dm1DmRx and is undefined if mefSoamDmCfgType is dm1DmTx.";
        reference   
         "[MEF SOAM-PM] R66, R100";
      }
    }


    /* XXX table comments here XXX */

    list mefSoamDmHistoryStatsBinsEntry {

      key "dot1agCfmMdIndex dot1agCfmMaIndex 
           dot1agCfmMepIdentifier mefSoamDmCfgIndex 
           mefSoamDmHistoryStatsIndex mefSoamDmCfgMeasBinType 
           mefSoamDmCfgMeasBinNumber";
      description   
       "The conceptual row of mefSoamDmHistoryStatsBinsTable";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamDmCfgIndex {
        type leafref {
          path "/mef-soam-pm:mefSoamPmDmObjects/mef-soam-pm:mefSoamDmCfgEntry/mef-soam-pm:mefSoamDmCfgIndex";
        }
        config true;
        description 
         "Automagically generated leafref leaf.";
      }
      leaf mefSoamDmHistoryStatsIndex {
        type leafref {
          path "/mef-soam-pm:mefSoamPmDmObjects/mef-soam-pm:mefSoamDmHistoryStatsEntry/mef-soam-pm:mefSoamDmHistoryStatsIndex";
        }
        description 
         "Automagically generated leafref leaf.";
      }
      leaf mefSoamDmCfgMeasBinType {
        type mef-soam:MefSoamTcDelayMeasurementBinType;
        description 
         "Automagically generated leafref leaf.";
      }
      leaf mefSoamDmCfgMeasBinNumber {
        type leafref {
          path "/mef-soam-pm:mefSoamPmDmObjects/mef-soam-pm:mefSoamDmCfgMeasBinEntry/mef-soam-pm:mefSoamDmCfgMeasBinNumber";
        }
        description 
         "Automagically generated leafref leaf.";
      }

      leaf mefSoamDmHistoryStatsBinsCounter {
        type yang:gauge32;
        description 
         "This object contains the count of the number of completed
          measurements initiated in this Measurement Interval whose value
          falls within the range specified for this bin (that is, greater
          than or equal to the measurement boundary for the bin, and
          (unless the bin is the last bin) less than the measurement
          boundary for the following bin.";
        reference   
         "[MEF SOAM-PM] R66, R67, R100, R101";
      }
    }


    /* XXX table comments here XXX */

    list mefSoamDmThresholdCfgEntry {

      key "dot1agCfmMdIndex dot1agCfmMaIndex 
           dot1agCfmMepIdentifier mefSoamDmCfgIndex 
           mefSoamDmThresholdCfgIndex";
      description   
       "The conceptual row of mefSoamDmThresholdCfgTable.";

      leaf dot1agCfmMdIndex {
        type leafref {
          path "/ieee8021-cfm:dot1agCfmMd/ieee8021-cfm:dot1agCfmMdEntry/ieee8021-cfm:dot1agCfmMdIndex";
        }
        config true;
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        config true;
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        config true;
        description 
         "Automagically generated leafref leaf.";
      }
      leaf mefSoamDmCfgIndex {
        type leafref {
          path "/mef-soam-pm:mefSoamPmDmObjects/mef-soam-pm:mefSoamDmCfgEntry/mef-soam-pm:mefSoamDmCfgIndex";
        }
        config true;
        description 
         "Automagically generated leafref leaf.";
      }

      leaf mefSoamDmThresholdCfgIndex {
        type uint32 {
          range "1..4294967295";
        }
        description 
         "The index of the threshold number for the specific DM
          threshold entry. 
          
          An index value of '1' is to be supported. Other index values
          can be supported.";
      }

      leaf mefSoamDmThresholdCfgEnable {
        type bits {
          bit bMefSoamDmMeasuredFrameDelayTwoWayThreshold   { position 0; }
          bit bMefSoamDmMaxFrameDelayTwoWayThreshold        { position 1; }
          bit bMefSoamDmAvgFrameDelayTwoWayThreshold        { position 2; }
          bit bMefSoamDmMeasuredIfdvTwoWayThreshold         { position 3; }
          bit bMefSoamDmMaxIfdvTwoWayThreshold              { position 4; }
          bit bMefSoamDmAvgIfdvTwoWayThreshold              { position 5; }
          bit bMefSoamDmMaxFrameDelayRangeTwoWayThreshold   { position 6; }
          bit bMefSoamDmAvgFrameDelayRangeTwoWayThreshold   { position 7; }
          bit bMefSoamDmMeasuredFrameDelayForwardThreshold  { position 8; }
          bit bMefSoamDmMaxFrameDelayForwardThreshold       { position 9; }
          bit bMefSoamDmAvgFrameDelayForwardThreshold       { position 10; }
          bit bMefSoamDmMeasuredIfdvForwardThreshold        { position 11; }
          bit bMefSoamDmMaxIfdvForwardThreshold             { position 12; }
          bit bMefSoamDmAvgIfdvForwardThreshold             { position 13; }
          bit bMefSoamDmMaxFrameDelayRangeForwardThreshold  { position 14; }
          bit bMefSoamDmAvgFrameDelayRangeForwardThreshold  { position 15; }
          bit bMefSoamDmMeasuredFrameDelayBackwardThreshold { position 16; }
          bit bMefSoamDmMaxFrameDelayBackwardThreshold      { position 17; }
          bit bMefSoamDmAvgFrameDelayBackwardThreshold      { position 18; }
          bit bMefSoamDmMeasuredIfdvBackwardThreshold       { position 19; }
          bit bMefSoamDmMaxIfdvBackwardThreshold            { position 20; }
          bit bMefSoamDmAvgIfdvBackwardThreshold            { position 21; }
          bit bMefSoamDmMaxFrameDelayRangeBackwardThreshold { position 22; }
          bit bMefSoamDmAvgFrameDelayRangeBackwardThreshold { position 23; }
        }
        config true;
        description 
         "A vector of bits that indicates the type of SOAM DM threshold 
          notifications that are enabled. 
          
          A bit set to '1' enables the specific SOAM DM threshold notification
          and when the specific counter is enabled and the threshold is crossed a 
          notification is generated. 
          
          A bit set to '0' disables the specific SOAM DM threshold notification.
          
          If a particular SOAM DM threshold is not supported the BIT value is
          set to '0'.
          
          bMefSoamDmMeasuredFrameDelayTwoWayThreshold(0) 
                  Enables/disables measured frame two-way delay threshold 
                  notification. The notification is sent immediately when the
                  mefSoamDmMeasuredStatsFrameDelayTwoWay value is 
                  greater than or equal to threshold value.
          bMefSoamDmMaxFrameDelayTwoWayThreshold(1) 
                  Enables/disables maximum frame two-way delay threshold 
                  notification. The notification is sent immediately when the
                  mefSoamDmCurrentStatsFrameDelayTwoWayMax value is 
                  greater than or equal to threshold value in a Measurement Interval.
          bMefSoamDmAvgFrameDelayTwoWayThreshold(2)
                  Enables/disables average frame two-way delay threshold
                  notification. The notification is sent when at the end of a
                  Measurement Interval if the 
                  mefSoamDmCurrentStatsFrameDelayTwoWayAvg value is 
                  greater than or equal to the threshold value.
          bMefSoamDmMeasuredIfdvTwoWayThreshold(3)
                  Enables/disables measured frame IFDV two-way threshold 
                  notification. The notification is sent immediately when the
                  mefSoamDmMeasuredStatsIfdvTwoWay value is greater
                  than or equal to threshold value.
          bMefSoamDmMaxIfdvTwoWayThreshold(4)
                  Enables/disables maximum frame IFDV two-way threshold 
                  notification. The notification is sent immediately when the
                  mefSoamDmCurrentStatsIfdvTwoWayMax value is greater
                  than or equal to threshold value in a Measurement Interval.
          bMefSoamDmAvgIfdvTwoWayThreshold(5)
                  Enables/disables average frame IFDV two-way threshold
                  notification. The notification is sent when at the end of a
                  Measurement Interval if the 
                  mefSoamDmCurrentStatsIfdvTwoWayAvg value is
                  greater than or equal to the threshold value.
          bMefSoamDmMaxFrameDelayRangeTwoWayThreshold(6)
                  Enables/disables maximum Frame Delay Range two-way threshold 
                  notification. The notification is sent immediately when the
                  mefSoamDmCurrentStatsFrameDelayRangeTwoWayMax value is greater
                  than or equal to threshold value in a Measurement Interval.
          bMefSoamDmAvgFrameDelayRangeTwoWayThreshold(7)
                  Enables/disables average Frame Delay Range two-way threshold
                  notification. The notification is sent when at the end of a
                  Measurement Interval if the 
                  mefSoamDmCurrentStatsFrameDelayRangeTwoWayAvg value is
                  greater than or equal to the threshold value.
          bMefSoamDmMeasuredFrameDelayForwardThreshold(8)
                  Enables/disables measured forward frame delay threshold
                  notification. The notification is sent immediately when the
                  mefSoamDmMeasuredStatsFrameDelayForward value is
                  greater than or equal to threshold value.
          bMefSoamDmMaxFrameDelayForwardThreshold(9)
                  Enables/disables maximum forward frame delay threshold
                  notification. The notification is sent immediately when the
                  mefSoamDmCurrentStatsFrameDelayForwardMax value is
                  greater than or equal to threshold value in a Measurement Interval.
          bMefSoamDmAvgFrameDelayForwardThreshold(10)
                  Enables/disables average forward frame delay threshold
                  notification. The notification is sent when at the end of a
                  Measurement Interval if the 
                  mefSoamDmCurrentStatsFrameDelayForwardAvg value is
                  greater than or equal to the threshold value.
          bMefSoamDmMeasuredIfdvForwardThreshold(11)
                  Enables/disables measured frame IFDV forward threshold 
                  notification. The notification is sent immediately when the
                  mefSoamDmMeasuredStatsIfdvForward value is greater
                  than or equal to threshold value.
          bMefSoamDmMaxIfdvForwardThreshold(12)
                  Enables/disables maximum frame IFDV forward threshold 
                  notification. The notification is sent immediately when the
                  mefSoamDmCurrentStatsIfdvForwardMax value is greater
                  than or equal to threshold value in a Measurement Interval.
          bMefSoamDmAvgIfdvForwardThreshold(13)
                  Enables/disables average frame IFDV forward threshold
                  notification. The notification is sent when at the end of a
                  Measurement Interval if the 
                  mefSoamDmCurrentStatsIfdvForwardAvg value is 
                  greater than or equal to the threshold value.
          bMefSoamDmMaxFrameDelayRangeForwardThreshold(14)
                  Enables/disables maximum Frame Delay Range forward threshold 
                  notification. The notification is sent immediately when the
                  mefSoamDmCurrentStatsFrameDelayRangeForwardMax value is greater
                  than or equal to threshold value in a Measurement Interval.
          bMefSoamDmAvgFrameDelayRangeForwardThreshold(15)
                  Enables/disables average Frame Delay Range forward threshold
                  notification. The notification is sent when at the end of a
                  Measurement Interval if the 
                  mefSoamDmCurrentStatsFrameDelayRangeForwardAvg value is 
                  greater than or equal to the threshold value.
          bMefSoamDmMeasuredFrameDelayBackwardThreshold(16)
                  Enables/disables measured backward frame delay threshold
                  notification. The notification is sent immediately when the
                  mefSoamDmMeasuredStatsFrameDelayBackward value is
                  greater than or equal to threshold value.
          bMefSoamDmMaxFrameDelayBackwardThreshold(17)
                  Enables/disables maximum backward frame delay threshold
                  notification. The notification is sent immediately when the
                  mefSoamDmCurrentStatsFrameDelayBackwardMax value is
                  greater than or equal to threshold value in a 
                  Measurement Interval.
          bMefSoamDmAvgFrameDelayBackwardThreshold(18)
                  Enables/disables average backward frame delay threshold
                  notification. The notification is sent when at the end of a
                  Measurement Interval if the 
                  mefSoamDmCurrentStatsFrameDelayBackwardAvg value is
                  greater than or equal to the threshold value.
          bMefSoamDmMeasuredIfdvBackwardThreshold(19)
                  Enables/disables measured frame IFDV backward threshold 
                  notification. The notification is sent immediately when the
                  mefSoamDmMeasuredStatsIfdvBackward value is greater
                  than or equal to threshold value.
          bMefSoamDmMaxIfdvBackwardThreshold(20)
                  Enables/disables maximum frame IFDV backward threshold 
                  notification. The notification is sent immediately when the
                  mefSoamDmCurrentStatsIfdvBackwardMax value is greater
                  than or equal to threshold value in a Measurement Interval.
          bMefSoamDmAvgIfdvBackwardThreshold(21)
                  Enables/disables average frame IFDV backward threshold
                  notification. The notification is sent when at the end of a
                  Measurement Interval if the 
                  mefSoamDmCurrentStatsIfdvBackwardAvg value is greater
                  than or equal to the threshold value.
          bMefSoamDmMaxFrameDelayRangeBackwardThreshold(22)
                  Enables/disables maximum Frame Delay Range backward threshold 
                  notification. The notification is sent immediately when the
                  mefSoamDmCurrentStatsFrameDelayRangeBackwardMax value is greater
                  than or equal to threshold value in a Measurement Interval.
          bMefSoamDmAvgFrameDelayRangeBackwardThreshold(23)
                  Enables/disables average Frame Delay Range backward threshold
                  notification. The notification is sent when at the end of a
                  Measurement Interval if the 
                  mefSoamDmCurrentStatsFrameDelayRangeBackwardAvg value is greater
                  than or equal to the threshold value.";
      }

      leaf mefSoamDmThresholdCfgMeasuredFrameDelayTwoWayThreshold {
        type uint32;
        units "microseconds";
        config true;
        description 
         "This object is used to set the measurement two-way delay threshold
          value that will be used to determine if a threshold notification is
          generated.";
      }

      leaf mefSoamDmThresholdCfgMaxFrameDelayTwoWayThreshold {
        type uint32;
        units "microseconds";
        config true;
        description 
         "This object is used to set the maximum two-way delay threshold
          value that will be used to determine if a threshold notification is
          generated.";
      }

      leaf mefSoamDmThresholdCfgAvgFrameDelayTwoWayThreshold {
        type uint32;
        units "microseconds";
        config true;
        description 
         "This object is used to set the average two-way delay threshold
          value that will be used to determine if a threshold notification is
          generated.";
      }

      leaf mefSoamDmThresholdCfgMeasuredIfdvTwoWayThreshold {
        type uint32;
        units "microseconds";
        config true;
        description 
         "This object is used to set the measurement two-way IFDV threshold
          value that will be used to determine if a threshold notification is
          generated.";
      }

      leaf mefSoamDmThresholdCfgMaxIfdvTwoWayThreshold {
        type uint32;
        units "microseconds";
        config true;
        description 
         "This object is used to set the maximum two-way IFDV threshold
          value that will be used to determine if a threshold notification is
          generated.";
      }

      leaf mefSoamDmThresholdCfgAvgIfdvTwoWayThreshold {
        type uint32;
        units "microseconds";
        config true;
        description 
         "This object is used to set the average two-way IFDV threshold
          value that will be used to determine if a threshold notification is
          generated.";
      }

      leaf mefSoamDmThresholdCfgMaxFrameDelayRangeTwoWayThreshold {
        type uint32;
        units "microseconds";
        config true;
        description 
         "This object is used to set the maximum two-way Frame Delay Range threshold
          value that will be used to determine if a threshold notification is
          generated.";
      }

      leaf mefSoamDmThresholdCfgAvgFrameDelayRangeTwoWayThreshold {
        type uint32;
        units "microseconds";
        config true;
        description 
         "This object is used to set the average two-way Frame Delay Range threshold
          value that will be used to determine if a threshold notification is
          generated.";
      }

      leaf mefSoamDmThresholdCfgMeasuredFrameDelayForwardThreshold {
        type uint32;
        units "microseconds";
        config true;
        description 
         "This object is used to set the measurement forward delay threshold
          value that will be used to determine if a threshold notification is
          generated.";
      }

      leaf mefSoamDmThresholdCfgMaxFrameDelayForwardThreshold {
        type uint32;
        units "microseconds";
        config true;
        description 
         "This object is used to set the maximum forward delay threshold
          value that will be used to determine if a threshold notification is
          generated.";
      }

      leaf mefSoamDmThresholdCfgAvgFrameDelayForwardThreshold {
        type uint32;
        units "microseconds";
        config true;
        description 
         "This object is used to set the average forward delay threshold
          value that will be used to determine if a threshold notification is
          generated.";
      }

      leaf mefSoamDmThresholdCfgMeasuredIfdvForwardThreshold {
        type uint32;
        units "microseconds";
        config true;
        description 
         "This object is used to set the measurement IFDV threshold
          value that will be used to determine if a threshold notification is
          generated.";
      }

      leaf mefSoamDmThresholdCfgMaxIfdvForwardThreshold {
        type uint32;
        units "microseconds";
        config true;
        description 
         "This object is used to set the maximum IFDV threshold
          value that will be used to determine if a threshold notification is
          generated.";
      }

      leaf mefSoamDmThresholdCfgAvgIfdvForwardThreshold {
        type uint32;
        units "microseconds";
        config true;
        description 
         "This object is used to set the average IFDV threshold
          value that will be used to determine if a threshold notification is
          generated.";
      }

      leaf mefSoamDmThresholdCfgMaxFrameDelayRangeForwardThreshold {
        type uint32;
        units "microseconds";
        config true;
        description 
         "This object is used to set the maximum Frame Delay Range threshold
          value that will be used to determine if a threshold notification is
          generated.";
      }

      leaf mefSoamDmThresholdCfgAvgFrameDelayRangeForwardThreshold {
        type uint32;
        units "microseconds";
        config true;
        description 
         "This object is used to set the average Frame Delay Range threshold
          value that will be used to determine if a threshold notification is
          generated.";
      }

      leaf mefSoamDmThresholdCfgMeasuredFrameDelayBackwardThreshold {
        type uint32;
        units "microseconds";
        config true;
        description 
         "This object is used to set the measurement backward delay threshold
          value that will be used to determine if a threshold notification is
          generated.";
      }

      leaf mefSoamDmThresholdCfgMaxFrameDelayBackwardThreshold {
        type uint32;
        units "microseconds";
        config true;
        description 
         "This object is used to set the maximum backward delay threshold
          value that will be used to determine if a threshold notification is
          generated.";
      }

      leaf mefSoamDmThresholdCfgAvgFrameDelayBackwardThreshold {
        type uint32;
        units "microseconds";
        config true;
        description 
         "This object is used to set the average backward delay threshold
          value that will be used to determine if a threshold notification is
          generated.";
      }

      leaf mefSoamDmThresholdCfgMeasuredIfdvBackwardThreshold {
        type uint32;
        units "microseconds";
        config true;
        description 
         "This object is used to set the measurement backward IFDV threshold
          value that will be used to determine if a threshold notification is
          generated.";
      }

      leaf mefSoamDmThresholdCfgMaxIfdvBackwardThreshold {
        type uint32;
        units "microseconds";
        config true;
        description 
         "This object is used to set the maximum backward IFDV threshold
          value that will be used to determine if a threshold notification is
          generated.";
      }

      leaf mefSoamDmThresholdCfgAvgIfdvBackwardThreshold {
        type uint32;
        units "microseconds";
        config true;
        description 
         "This object is used to set the average backward IFDV threshold
          value that will be used to determine if a threshold notification is
          generated.";
      }

      leaf mefSoamDmThresholdCfgMaxFrameDelayRangeBackwardThreshold {
        type uint32;
        units "microseconds";
        config true;
        description 
         "This object is used to set the maximum backward Frame Delay Range threshold
          value that will be used to determine if a threshold notification is
          generated.";
      }

      leaf mefSoamDmThresholdCfgAvgFrameDelayRangeBackwardThreshold {
        type uint32;
        units "microseconds";
        config true;
        description 
         "This object is used to set the average backward Frame Delay Range threshold
          value that will be used to determine if a threshold notification is
          generated.";
      }

      leaf mefSoamDmThresholdCfgRowStatus {
        type smiv2:RowStatus;
        config true;
        description 
         "The status of the row.
          
          The writable columns in a row cannot be changed if the row
          is active. All columns are to have a valid value before a row
          can be activated.";
      }
    }
  }

  container mefSoamPmNotificationCfg {

    leaf mefSoamPmNotificationCfgAlarmInterval {
      type uint32 {
        range "0..60";
      }
      units "Seconds";
      config true;
      description   
       "A value indicating the shortest time interval in seconds between the
        generation of the same notification type per PM session to the list of 
        notification destinations. An agent generates the first notification
        of given type for a given PM session immediately. An agent is not to
        generate a second specific notification of the same type for the same
        MEP for the same session until the time interval has expired. A value of zero 
        indicates that all notifications are sent immediately upon detection 
        of the condition.";
    }

    leaf mefSoamPmNotificationCfgAlarmEnable {
      type bits {
        bit bAvailabilityChangeAlarm  { position 0; }
        bit bLmSessionStartStopAlarm  { position 1; }
        bit bDmSessionStartStopAlarm  { position 2; }
        bit bPmThresholdAboveAlarm    { position 3; }
        bit bPmThresholdSetClearAlarm { position 4; }
      }
      config true;
      description   
       "A vector of bits that indicates whether a specific notification is
        enabled. 
        
        A bit set to '1' enables the specific notification generation. 
        
        A bit set to '0' disables the specific notification.
        
        If a particular alarm is not supported the BIT value of the enable/disable
        is set to '0'.
        
        bAvailabilityChangeAlarm(0)  enables/disables mefSoamAvailabilityChangeAlarm
        bLmSessionStartStopAlarm(1)  enables/disables mefSoamLmSessionStartStopAlarm
        bDmSessionStartStopAlarm(2)  enables/disables mefSoamDmSessionStartStopAlarm
        bPmThresholdAboveAlarm(3)    enables/disables mefSoamPmThresholdAboveAlarm
        bPmThresholdSetClearAlarm(4) enables/disables mefSoamPmThresholdSetClearAlarm";
    }
  }

  container mefSoamPmNotificationObj {

    leaf mefSoamPmNotificationObjDateAndTime {
      type smiv2:DateAndTime;
      description   
       "This object contains the time and date at the time that 
        the notification event is detected, not the time of the notification 
        generation.  
        
        This object is used only for notifications. The mechanism to set and keep
        current the date and time is not specified.";
    }

    leaf mefSoamPmNotificationObjThresholdId {
      type yang:object-identifier;
      description   
       "The Object Identifier of the object that caused the generation of the
        notification from the mefSoamLmThresholdEntry or mefSoamDmThresholdEntry.
        
        This object is only used for the notification.";
    }

    leaf mefSoamPmNotificationObjThresholdConfig {
      type uint32;
      description   
       "The configured threshold value of the object that caused the generation
        of the notification.
        
        This object is only used for the notification.";
    }

    leaf mefSoamPmNotificationObjThresholdValue {
      type uint32;
      description   
       "The measured value of the object at the time of the generation of the
        Notification, from the mefSoamLmMeasuredStatsTable, 
        mefSoamLmCurrentStatsTable, mefSoamLmCurrentAvailStatsTable,
        mefSoamDmMeasuredStatsTable or mefSoamDmCurrentStatsTable.
        
        This object is only used for the notification.";
    }

    leaf mefSoamPmNotificationObjSuspect {
      type smiv2:TruthValue;
      description   
       "The suspect flag for the current Measurement Interval in which the
        notification was generated from the mefSoamLmCurrentStatsTable,
        mefSoamLmCurrentAvailStatsTable, or mefSoamDmCurrentStatsTable.
        
        This object is only used for the notification.";
    }

    leaf mefSoamPmNotificationObjCrossingType {
      type enumeration {
        enum aboveAlarm { value 1; }
        enum setAlarm   { value 2; }
        enum clearAlarm { value 3; }
      }
      description   
       "The Notification Crossing Type of the object that caused the generation
        of the notification from the mefSoamLmThresholdEntry or 
        mefSoamDmThresholdEntry.
        
        aboveAlarm(1)   indicates that the crossing type alarm was an above
                        threshold
        
        setAlarm(2)     indicates that the crossing type alarm was a set
                        threshold
        
        clearAlarm(3)   indicates that the crossing type alarm was a clear
                        threshold
        
        This object is only used for the notification.";
    }

    leaf mefSoamPmNotificationObjDestinationMep {
      type yang:mac-address;
      description   
       "The MAC address of the Destination MEP associated the notification found
        in either the mefSoamDmCfgTable or mefSoamLmCfgTable.
        
        This object is only used for the notification.";
    }

    leaf mefSoamPmNotificationObjPriority {
      type yang:mac-address;
      description   
       "The CoS priority of the associated notification found
        in either the mefSoamDmCfgTable or mefSoamLmCfgTable.
        
        This object is only used for the notification.";
    }
  }


  /* XXX table comments here XXX */

  augment "/ieee8021-cfm:dot1agCfmMep/ieee8021-cfm:dot1agCfmMepEntry" {
    description     
     "The conceptual row of mefSoamPmMepTable.";

    leaf mefSoamPmMepOperNextIndex {
      type ieee8021-cfm:Dot1afCfmIndexIntegerNextFree;
      description   
       "This object contains an unused value for a PM session number on a 
        MEP that can be used for either LM or DM sessions, or a zero to 
        indicate that none exist. This value needs to be read in order to
        find an available index for row-creation of a PM session on a MEP and
        then used when a row is created. This value is automatically updated
        by the SNMP Agent after the row is created.
        
        Referential integrity is necessary, i.e., the index needs to be
        persistent upon a reboot or restart of a device.  The index
        is never to be reused for other PM sessions on the same MEP while this
        session is active, or until it wraps to zero.  The index value keeps
        increasing up to that time. This is to facilitate access control based
        on a fixed index for an EMS, since the index is not reused.
        
        This object is an extension of the dot1agCfmMepTable and the object is
        automatically added or deleted based upon row creation and destruction
        of the dot1agCfmMepTable.";
    }

    leaf mefSoamPmMepLmSingleEndedResponder {
      type smiv2:TruthValue;
      config true;
      description   
       "This object specifies whether the Loss Measurement (LMM) single-ended
        Responder is enabled. 
        
        The value 'true' indicates the single-ended Loss Measurement Responder
        is enabled and if a LMM message is received a LMR will be sent in reply. 
        
        The value 'false' indicates the single-ended Loss Measurement Responder
        is disabled. If a LMM message is received no response will be sent and
        the message will be discarded. 
        
        This object needs to be persistent upon reboot or restart of a device.
        
        A MEP can be both a single-ended Responder and Controller simultaneously.";
    }

    leaf mefSoamPmMepSlmSingleEndedResponder {
      type smiv2:TruthValue;
      config true;
      description   
       "This object specifies whether the Synthetic Loss Measurement (SLM)
        single-ended Responder is enabled.  
        
        The value 'true' indicates the single-ended SLM Responder is enabled and
        if a SLM message is received a SLR will be sent in reply.
        
        The value 'false' indicates the single-ended SLM Responder is disabled.
        If a SLM message is received no response will be sent and the message 
        will be discarded.
        
        This object needs to be persistent upon reboot or restart of a device.
        
        A MEP can be both a single-ended Responder and Controller simultaneously.";
    }

    leaf mefSoamPmMepDmSingleEndedResponder {
      type smiv2:TruthValue;
      config true;
      description   
       "This object specifies whether the Delay Measurement (DMM) single
        ended Responder is enabled. 
        
        The value 'true' indicates the single-ended Delay Measurement Responder
        is enabled and if a DMM message is received a DMR will be sent in reply.
        
        The value 'false' indicates the single-ended Delay Measurement Responder
        is disabled. If a DMM message is received no response will be sent and 
        the message will be discarded.
        
        This object needs to be persistent upon reboot or restart of a device.
        
        A MEP can be both a single-ended Responder and Controller simultaneously.";
    }
  }

  notification mefSoamAvailabilityChangeAlarm {
    description     
     "An mefSoamAvailabilityChangeAlarm notification is sent when the state of
      mefSoamLmMeasuredStatsAvailForwardStatus or 
      mefSoamLmMeasuredStatsAvailBackwardStatus changes. 
      
      The management entity that receives the notification can identify
      the system from the network source address of the notification,
      and can identify the PM session reporting the change
      by the indices in the OID 
      mefSoamLmMeasuredStatsAvailForwardLastTransitionTime, including
      dot1agCfmMdIndex, dot1agCfmMaIndex, dot1agCfmMepIdentifier, and 
      mefSoamLmCfgIndex.
      
      An agent is not to generate more than one mefSoamAvailabilityChangeAlarm
      'notification-event' in a given time interval per PM session as 
      specified by the mefSoamPmNotificationCfgAlarmInterval.  A 
      'notification-event' is the transmission of a single notification to
      a list of notification destinations.
      
      If additional availability state changes occur within the 
      mefSoamPmNotificationCfgAlarmInterval period, then notification 
      generation for these changes are suppressed by the agent until 
      the current alarm interval expires. At the end of an alarm interval 
      period, one notification-event is generated if any availability
      state changes occurred since the start of the alarm interval period. 
      In such a case, another alarm interval period is started right away.";
    reference       
     "[MEF SOAM-PM] R83, R84";

    container mefSoamAvailabilityChangeAlarm-mefSoamPmNotificationObjDateAndTime {
      leaf mefSoamPmNotificationObjDateAndTime {
        type smiv2:DateAndTime;
        description 
         "This object contains the time and date at the time that 
          the notification event is detected, not the time of the notification 
          generation.  
          
          This object is used only for notifications. The mechanism to set and keep
          current the date and time is not specified.";
      }
    }

    container mefSoamAvailabilityChangeAlarm-mefSoamLmMeasuredStatsAvailForwardStatus {
      leaf dot1agCfmMdIndex {
        type leafref {
          path "/ieee8021-cfm:dot1agCfmMd/ieee8021-cfm:dot1agCfmMdEntry/ieee8021-cfm:dot1agCfmMdIndex";
        }
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        description 
         "Automagically generated leafref leaf.";
      }
      leaf mefSoamLmMeasuredStatsAvailForwardStatus {
        type mef-soam:MefSoamTcAvailabilityType;
        description 
         "This object indicates the availability status (the outcome of the
          last known availability indicator) in the forward direction.
          Note that the status of an availability indicator is not known until
          the loss for a number of subsequent availability indicators has been
          calculated (as determined by 
          mefSoamLmCfgAvailabilityNumConsecutiveIntervals)";
        reference   
         "[MEF SOAM-PM] R83";
      }
    }

    container mefSoamAvailabilityChangeAlarm-mefSoamLmMeasuredStatsAvailBackwardStatus {
      leaf dot1agCfmMdIndex {
        type leafref {
          path "/ieee8021-cfm:dot1agCfmMd/ieee8021-cfm:dot1agCfmMdEntry/ieee8021-cfm:dot1agCfmMdIndex";
        }
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        description 
         "Automagically generated leafref leaf.";
      }
      leaf mefSoamLmMeasuredStatsAvailBackwardStatus {
        type mef-soam:MefSoamTcAvailabilityType;
        description 
         "This object indicates the availability status (the outcome of the
          last availability indicator) in the backward direction.
          Note that the status of an availability indicator is not known until
          the loss for a number of subsequent availability indicators has been
          calculated (as determined by 
          mefSoamLmCfgAvailabilityNumConsecutiveIntervals)";
        reference   
         "[MEF SOAM-PM] R83";
      }
    }

    container mefSoamAvailabilityChangeAlarm-mefSoamLmMeasuredStatsAvailForwardLastTransitionTime {
      leaf dot1agCfmMdIndex {
        type leafref {
          path "/ieee8021-cfm:dot1agCfmMd/ieee8021-cfm:dot1agCfmMdEntry/ieee8021-cfm:dot1agCfmMdIndex";
        }
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        description 
         "Automagically generated leafref leaf.";
      }
      leaf mefSoamLmMeasuredStatsAvailForwardLastTransitionTime {
        type smiv2:DateAndTime;
        description 
         "This object indicates the time of the last transition
          between available and unavailable in the forward direction.
          
          If there have been no transitions since the Loss Measurement
          Session was started, this is set to 0.";
        reference   
         "[MEF SOAM-PM] R83";
      }
    }

    container mefSoamAvailabilityChangeAlarm-mefSoamLmMeasuredStatsAvailBackwardLastTransitionTime {
      leaf dot1agCfmMdIndex {
        type leafref {
          path "/ieee8021-cfm:dot1agCfmMd/ieee8021-cfm:dot1agCfmMdEntry/ieee8021-cfm:dot1agCfmMdIndex";
        }
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        description 
         "Automagically generated leafref leaf.";
      }
      leaf mefSoamLmMeasuredStatsAvailBackwardLastTransitionTime {
        type smiv2:DateAndTime;
        description 
         "This object indicates the time of the last transition
          between available and unavailable in the backward direction.
          
          If there have been no transitions since the Loss Measurement
          Session was started, this is set to 0.";
        reference   
         "[MEF SOAM-PM] R83";
      }
    }

    container mefSoamAvailabilityChangeAlarm-mefSoamLmCurrentAvailStatsForwardAvailable {
      leaf dot1agCfmMdIndex {
        type leafref {
          path "/ieee8021-cfm:dot1agCfmMd/ieee8021-cfm:dot1agCfmMdEntry/ieee8021-cfm:dot1agCfmMdIndex";
        }
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        description 
         "Automagically generated leafref leaf.";
      }
      leaf mefSoamLmCurrentAvailStatsForwardAvailable {
        type yang:gauge32;
        description 
         "This object contains the number of availability indicators 
          evaluated as available in the forward direction by this MEP during
          this Measurement Interval.";
        reference   
         "[MEF SOAM-PM] R87; [MEF 10.2.1]";
      }
    }

    container mefSoamAvailabilityChangeAlarm-mefSoamLmCurrentAvailStatsForwardUnavailable {
      leaf dot1agCfmMdIndex {
        type leafref {
          path "/ieee8021-cfm:dot1agCfmMd/ieee8021-cfm:dot1agCfmMdEntry/ieee8021-cfm:dot1agCfmMdIndex";
        }
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        description 
         "Automagically generated leafref leaf.";
      }
      leaf mefSoamLmCurrentAvailStatsForwardUnavailable {
        type yang:gauge32;
        description 
         "This object contains the number of availability indicators 
          evaluated as unavailable in the forward direction by this MEP during
          this Measurement Interval.";
        reference   
         "[MEF SOAM-PM] R87";
      }
    }

    container mefSoamAvailabilityChangeAlarm-mefSoamLmCurrentAvailStatsBackwardAvailable {
      leaf dot1agCfmMdIndex {
        type leafref {
          path "/ieee8021-cfm:dot1agCfmMd/ieee8021-cfm:dot1agCfmMdEntry/ieee8021-cfm:dot1agCfmMdIndex";
        }
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        description 
         "Automagically generated leafref leaf.";
      }
      leaf mefSoamLmCurrentAvailStatsBackwardAvailable {
        type yang:gauge32;
        description 
         "This object contains the number of availability indicators 
          evaluated as available in the backward direction by this MEP during
          this Measurement Interval.";
        reference   
         "[MEF SOAM-PM] R87";
      }
    }

    container mefSoamAvailabilityChangeAlarm-mefSoamLmCurrentAvailStatsBackwardUnavailable {
      leaf dot1agCfmMdIndex {
        type leafref {
          path "/ieee8021-cfm:dot1agCfmMd/ieee8021-cfm:dot1agCfmMdEntry/ieee8021-cfm:dot1agCfmMdIndex";
        }
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        description 
         "Automagically generated leafref leaf.";
      }
      leaf mefSoamLmCurrentAvailStatsBackwardUnavailable {
        type yang:gauge32;
        description 
         "This object contains the number of availability indicators 
          evaluated as unavailable in the backward direction by this MEP
          during this Measurement Interval.";
        reference   
         "[MEF SOAM-PM] R87";
      }
    }

    container mefSoamAvailabilityChangeAlarm-mefSoamPmNotificationObjDestinationMep {
      leaf mefSoamPmNotificationObjDestinationMep {
        type yang:mac-address;
        description 
         "The MAC address of the Destination MEP associated the notification found
          in either the mefSoamDmCfgTable or mefSoamLmCfgTable.
          
          This object is only used for the notification.";
      }
    }

    container mefSoamAvailabilityChangeAlarm-mefSoamPmNotificationObjPriority {
      leaf mefSoamPmNotificationObjPriority {
        type yang:mac-address;
        description 
         "The CoS priority of the associated notification found
          in either the mefSoamDmCfgTable or mefSoamLmCfgTable.
          
          This object is only used for the notification.";
      }
    }

  }

  notification mefSoamLmSessionStartStopAlarm {
    description     
     "An mefSoamLmSessionStartStopAlarm notification is sent when the state of
      mefSoamLmCfgSessionStatus changes. 
      
      The management entity that receives the notification can identify
      the system from the network source address of the notification,
      and can identify the individual PM session reporting the start/stop
      by the indices in the OID mefSoamLmCfgSessionStatus, including
      dot1agCfmMdIndex, dot1agCfmMaIndex, dot1agCfmMepIdentifier, and 
      mefSoamLmCfgIndex.
      
      An agent is not to generate more than one mefSoamLmSessionStartStopAlarm
      'notification-event' in a given time interval per LM session as specified
      by the mefSoamPmNotificationCfgAlarmInterval.  A 'notification-event' is
      the transmission of a single notification to a list of notification 
      destinations.
      
      If additional operational state changes occur within the 
      mefSoamPmNotificationCfgAlarmInterval period, then notification 
      generation for these changes are be suppressed by the agent until 
      the current alarm interval expires. At the end of an alarm interval 
      period, one notification-event is generated if any operational 
      state changes occurred since the start of the alarm interval period. In
      such a case, another alarm interval period is started right away.";

    container mefSoamLmSessionStartStopAlarm-mefSoamLmCfgSessionStatus {
      leaf dot1agCfmMdIndex {
        type leafref {
          path "/ieee8021-cfm:dot1agCfmMd/ieee8021-cfm:dot1agCfmMdEntry/ieee8021-cfm:dot1agCfmMdIndex";
        }
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        description 
         "Automagically generated leafref leaf.";
      }
      leaf mefSoamLmCfgIndex {
        type leafref {
          path "/mef-soam-pm:mefSoamPmLmObjects/mef-soam-pm:mefSoamLmCfgEntry/mef-soam-pm:mefSoamLmCfgIndex";
        }
        description 
         "Automagically generated leafref leaf.";
      }
      leaf mefSoamLmCfgSessionStatus {
        type mef-soam:MefSoamTcStatusType;
        description 
         "This object indicates the current status of the LM session. A value
          of 'active' indicates the current LM session is active, i.e. the current
          time lies between the start time and the stop time, and
          mefSoamLmCfgEnabled is true. A value of 'notActive' indicates the
          current LM session is not active, i.e. it has not started yet, has
          stopped upon reaching the stop time, or is disabled.";
      }
    }

    container mefSoamLmSessionStartStopAlarm-mefSoamPmNotificationObjDateAndTime {
      leaf mefSoamPmNotificationObjDateAndTime {
        type smiv2:DateAndTime;
        description 
         "This object contains the time and date at the time that 
          the notification event is detected, not the time of the notification 
          generation.  
          
          This object is used only for notifications. The mechanism to set and keep
          current the date and time is not specified.";
      }
    }

    container mefSoamLmSessionStartStopAlarm-mefSoamPmNotificationObjDestinationMep {
      leaf mefSoamPmNotificationObjDestinationMep {
        type yang:mac-address;
        description 
         "The MAC address of the Destination MEP associated the notification found
          in either the mefSoamDmCfgTable or mefSoamLmCfgTable.
          
          This object is only used for the notification.";
      }
    }

  }

  notification mefSoamDmSessionStartStopAlarm {
    description     
     "An mefSoamDmSessionStartStopAlarm notification is sent when the state of
      mefSoamDmCfgSessionStatus changes. 
      
      The management entity that receives the notification can identify
      the system from the network source address of the notification,
      and can identify the individual PM session reporting the start/stop
      by the indices in the OID mefSoamDmCfgSessionStatus, including
      dot1agCfmMdIndex, dot1agCfmMaIndex, dot1agCfmMepIdentifier, and 
      mefSoamDmCfgIndex.
      
      An agent is not to generate more than one mefSoamDmSessionStartStopAlarm
      'notification-event' in a given time interval per DM session as specified
      by mefSoamPmNotificationCfgAlarmInterval.  A 'notification-event' is the
      transmission of a single notification to a list of notification 
      destinations.
      
      If additional operational state changes occur within the 
      mefSoamPmNotificationCfgAlarmInterval period, then notification generation
      for these changes are suppressed by the agent until the current alarm 
      interval expires. At the end of an alarm interval period, one 
      notification-event is generated if any operational state changes
      occurred since the start of the alarm interval period. In such a case, 
      another alarm interval period is started right away.";

    container mefSoamDmSessionStartStopAlarm-mefSoamDmCfgSessionStatus {
      leaf dot1agCfmMdIndex {
        type leafref {
          path "/ieee8021-cfm:dot1agCfmMd/ieee8021-cfm:dot1agCfmMdEntry/ieee8021-cfm:dot1agCfmMdIndex";
        }
        description 
         "Automagically generated leafref leaf.";
      }
      leaf dot1agCfmMaIndex {
        type leafref {
          path "/ieee8021-cfm:dot1agCfmMa/ieee8021-cfm:dot1agCfmMaNetEntry/ieee8021-cfm:dot1agCfmMaIndex";
        }
        description 
         "Automagically generated leafref leaf.";
      }
      leaf dot1agCfmMepIdentifier {
        type leafref {
          path "/ieee8021-cfm:dot1agCfmMep/ieee8021-cfm:dot1agCfmMepEntry/ieee8021-cfm:dot1agCfmMepIdentifier";
        }
        description 
         "Automagically generated leafref leaf.";
      }
      leaf mefSoamDmCfgIndex {
        type leafref {
          path "/mef-soam-pm:mefSoamPmDmObjects/mef-soam-pm:mefSoamDmCfgEntry/mef-soam-pm:mefSoamDmCfgIndex";
        }
        description 
         "Automagically generated leafref leaf.";
      }
      leaf mefSoamDmCfgSessionStatus {
        type mef-soam:MefSoamTcStatusType;
        description 
         "This object indicates the current status of the DM session. A value
          of 'active' indicates the current DM session is active, i.e. the current
          time lies between the start time and the stop time, and 
          mefSoamDmCfgEnabled is true. A value of 'notActive' indicates the
          current DM session is not active, i.e. it has not started yet, has 
          stopped upon reaching the stop time, or is disabled.";
      }
    }

    container mefSoamDmSessionStartStopAlarm-mefSoamPmNotificationObjDateAndTime {
      leaf mefSoamPmNotificationObjDateAndTime {
        type smiv2:DateAndTime;
        description 
         "This object contains the time and date at the time that 
          the notification event is detected, not the time of the notification 
          generation.  
          
          This object is used only for notifications. The mechanism to set and keep
          current the date and time is not specified.";
      }
    }

    container mefSoamDmSessionStartStopAlarm-mefSoamPmNotificationObjDestinationMep {
      leaf mefSoamPmNotificationObjDestinationMep {
        type yang:mac-address;
        description 
         "The MAC address of the Destination MEP associated the notification found
          in either the mefSoamDmCfgTable or mefSoamLmCfgTable.
          
          This object is only used for the notification.";
      }
    }

  }

  notification mefSoamPmThresholdCrossingAlarm {
    description     
     "An mefSoamPmThresholdCrossingAlarm notification is sent if the 
      following conditions are met for a particular type.
      
      For an aboveAlarm five conditions need to be met:
      
      a) measurement of the parameter is enabled via mefSoamLmCfgMeasurementEnable
         for a LM crossing or mefSoamDmCfgMeasurementEnable for a DM crossing; 
         and
      
      b) the parameter threshold is configured in the mefSoamLmThresholdCfgTable
         or mefSoamDmThresholdCfgTable; and 
      
      c) the threshold crossing type of bPmThresholdAboveAlarm is enabled; 
         and
      
      d) the measured value of the parameter exceeds the value configured in
         the mefSoamLmThresholdCfgTable for a LM crossing entry or
         mefSoamDmThresholdCfgTable for a DM crossing entry for a type of
         bPmThresholdAboveAlarm; and
      
      e) no previous mefSoamPmThresholdCrossingAlarm notifications with type
         aboveAlarm have been sent relating to the same threshold in the
         mefSoamLmThresholdCfgTable or mefSoamDmThresholdCfgTable and the
         same parameter, during this Measurement Interval.
      
      For a setAlarm five conditions need to be met:
      
      a) measurement of the parameter is enabled via mefSoamLmCfgMeasurementEnable
         for a LM crossing or mefSoamDmCfgMeasurementEnable for a DM crossing; 
         and
      
      b) the parameter threshold is configured in the mefSoamLmThresholdCfgTable
         or mefSoamDmThresholdCfgTable; and 
      
      c) the threshold crossing type of bPmThresholdSetClearAlarm is enabled; 
         and
      
      d) the measured value of the parameter exceeds the value configured in
         the mefSoamLmThresholdCfgTable for a LM crossing entry or
         mefSoamDmThresholdCfgTable for a DM crossing entry for a type of
         bPmThresholdSetClearAlarm for the Measurement Interval; and
      
      e) the previous measured value did not 
         exceed the value configured in the mefSoamLmThresholdCfgTable for
         a LM crossing entry or mefSoamDmThresholdCfgTable for a DM crossing
         entry for a type of bPmThresholdSetClearAlarm.
      
      For a clearAlarm five conditions need to be met:
      
      a) measurement of the parameter is enabled via mefSoamLmCfgMeasurementEnable
         for a LM crossing or mefSoamDmCfgMeasurementEnable for a DM crossing; 
         and
      
      b) the parameter threshold is configured in the mefSoamLmThresholdCfgTable
         or mefSoamDmThresholdCfgTable; and 
      
      c) the threshold crossing type of bPmThresholdSetClearAlarm is enabled; 
         and
      
      d) the measured value of the parameter did not exceed the value configured 
         in the mefSoamLmThresholdCfgTable for a LM crossing entry or
         mefSoamDmThresholdCfgTable for a DM crossing entry for a type of
         bPmThresholdSetClearAlarm for the Measurement Interval; and
      
      e) the previous measured value did  
         exceed the value configured in the mefSoamLmThresholdCfgTable for
         a LM crossing entry or mefSoamDmThresholdCfgTable for a DM crossing
         entry for a type of bPmThresholdSetClearAlarm.
      
      In the case of thresholds applied to a maximum or average measurement
      counter, the previous measured value is the value of the counter at the
      end of the preceding Measurement Interval.  In the case of thresholds
      applied to the last measured value, it is the previous measured value.
      
      The management entity that receives the notification can identify
      the system from the network source address of the notification,
      and can identify the LM or DM session reporting the threshold
      crossing by the indices in the mefSoamPmNotificationCfgThresholdId object,
      including dot1agCfmMdIndex, dot1agCfmMaIndex, dot1agCfmMepIdentifier, 
      and the mefSoamLmCfgIndex or mefSoamDmCfgIndex. 
      
      An agent is not to generate more than one mefSoamLmThresholdCrossingAlarm
      'notification-event' of a given type per LM or DM session as specified
      by mefSoamPmNotificationCfgAlarmInterval. A 'notification-event' is the
      transmission of a single notification to a list of notification
      destinations.
      
      If additional threshold crossing events occur within the 
      mefSoamPmNotificationCfgAlarmInterval period, then notification 
      generation for these changes are suppressed by the agent until 
      the current alarm interval expires. At the end of an alarm interval 
      period, one notification-event is generated if any threshold
      crossing events occurred since the start of the alarm interval period. 
      In such a case, another alarm interval period is started right away.";

    container mefSoamPmThresholdCrossingAlarm-mefSoamPmNotificationObjCrossingType {
      leaf mefSoamPmNotificationObjCrossingType {
        type enumeration {
          enum aboveAlarm { value 1; }
          enum setAlarm   { value 2; }
          enum clearAlarm { value 3; }
        }
        description 
         "The Notification Crossing Type of the object that caused the generation
          of the notification from the mefSoamLmThresholdEntry or 
          mefSoamDmThresholdEntry.
          
          aboveAlarm(1)   indicates that the crossing type alarm was an above
                          threshold
          
          setAlarm(2)     indicates that the crossing type alarm was a set
                          threshold
          
          clearAlarm(3)   indicates that the crossing type alarm was a clear
                          threshold
          
          This object is only used for the notification.";
      }
    }

    container mefSoamPmThresholdCrossingAlarm-mefSoamPmNotificationObjThresholdId {
      leaf mefSoamPmNotificationObjThresholdId {
        type yang:object-identifier;
        description 
         "The Object Identifier of the object that caused the generation of the
          notification from the mefSoamLmThresholdEntry or mefSoamDmThresholdEntry.
          
          This object is only used for the notification.";
      }
    }

    container mefSoamPmThresholdCrossingAlarm-mefSoamPmNotificationObjThresholdConfig {
      leaf mefSoamPmNotificationObjThresholdConfig {
        type uint32;
        description 
         "The configured threshold value of the object that caused the generation
          of the notification.
          
          This object is only used for the notification.";
      }
    }

    container mefSoamPmThresholdCrossingAlarm-mefSoamPmNotificationObjThresholdValue {
      leaf mefSoamPmNotificationObjThresholdValue {
        type uint32;
        description 
         "The measured value of the object at the time of the generation of the
          Notification, from the mefSoamLmMeasuredStatsTable, 
          mefSoamLmCurrentStatsTable, mefSoamLmCurrentAvailStatsTable,
          mefSoamDmMeasuredStatsTable or mefSoamDmCurrentStatsTable.
          
          This object is only used for the notification.";
      }
    }

    container mefSoamPmThresholdCrossingAlarm-mefSoamPmNotificationObjSuspect {
      leaf mefSoamPmNotificationObjSuspect {
        type smiv2:TruthValue;
        description 
         "The suspect flag for the current Measurement Interval in which the
          notification was generated from the mefSoamLmCurrentStatsTable,
          mefSoamLmCurrentAvailStatsTable, or mefSoamDmCurrentStatsTable.
          
          This object is only used for the notification.";
      }
    }

    container mefSoamPmThresholdCrossingAlarm-mefSoamPmNotificationObjDateAndTime {
      leaf mefSoamPmNotificationObjDateAndTime {
        type smiv2:DateAndTime;
        description 
         "This object contains the time and date at the time that 
          the notification event is detected, not the time of the notification 
          generation.  
          
          This object is used only for notifications. The mechanism to set and keep
          current the date and time is not specified.";
      }
    }

    container mefSoamPmThresholdCrossingAlarm-mefSoamPmNotificationObjDestinationMep {
      leaf mefSoamPmNotificationObjDestinationMep {
        type yang:mac-address;
        description 
         "The MAC address of the Destination MEP associated the notification found
          in either the mefSoamDmCfgTable or mefSoamLmCfgTable.
          
          This object is only used for the notification.";
      }
    }

  }
} /* end of module MEF-SOAM-PM-MIB */
