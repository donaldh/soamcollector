/*
 * This module has been generated by smidump 0.4.8:
 *
 *      smidump -f yang TOKEN-RING-RMON-MIB
 *
 * Do not edit. Edit the source file instead!
 */

module TOKEN-RING-RMON-MIB {

  /*** NAMESPACE / PREFIX DEFINITION ***/

  namespace "urn:ietf:params:xml:ns:yang:smiv2:TOKEN-RING-RMON-MIB";
  prefix "token-ring";

  /*** LINKAGE (IMPORTS / INCLUDES) ***/

  /*** META INFORMATION ***/

  organization      
   "";

  contact           
   "";

  description       
   "";

  /*** TYPE DEFINITIONS ***/

  typedef MacAddress {
    type binary {
      length "6";
    }
  }

  typedef TimeInterval {
    type int32;
  }

} /* end of module TOKEN-RING-RMON-MIB */
